;;; MEDDuctbankTest.lsp - headless checks for Support\MEDDuctbank.lsp (not shipped).
;;; Run after DUCTBANK in accoreconsole (see MEDDuctbankTest.ps1). Writes a report to *DBKT-OUT*.
;;; BOM check: MEDProcessSQLStatement is wrapped so INSERT / DELETE statements are captured,
;;; not executed (the test never writes to the MED database); SELECTs pass through.
;;; MVP3: stub-up encasement turn-up checks (*DBKT-TURNUPS*, *DBKT-ENCZ*), plain 3D polyline
;;; reference (DBKTPLAIN), DBEDIT round trip (DBKTEDITPRE / DBKTEDIT / DBKTEDITCHK).
;;; MVP4: route profile (slopes taken up by flex, vertical bends) and 45 deg stub-ups (open riser top,
;;; no fitting): DBKTROUTE (plain 3DPOLY test route from *DBKT-ROUTE*), DBKTPROF (profile / 45 / cover
;;; checks), DBKTBUBCOUNT / DBKTOLDBUB / DBKTDELCHK (banks built by e91df9d with BUBs: DBEDIT / DBDELETE).
(defun dbkt-w (s) (write-line s *DBKT-F*) (princ (strcat "\n[T] " s)))
(defun dbkt-check (name ok msg)
  (if ok (setq *DBKT-PASS* (1+ *DBKT-PASS*)) (setq *DBKT-FAIL* (cons (strcat name ": " msg) *DBKT-FAIL*)))
  (dbkt-w (strcat (if ok "PASS " "FAIL ") name (if (and msg (/= msg "")) (strcat "  " msg) ""))))
(defun dbkt-ents (role / ss i e out)
  (setq ss (ssget "_X" '((-3 ("DBANK_DATA")))) i 0)
  (if ss (repeat (sslength ss) (setq e (ssname ss i)) (if (or (null role) (= (dbk-xdval e "ROLE") role)) (setq out (cons e out))) (setq i (1+ i))))
  out)
(defun dbk-xdhandles (e / out)
  (foreach it (cdar (cdr (assoc -3 (entget e '("DBANK_DATA"))))) (if (= (car it) 1005) (setq out (cons (cdr it) out))))
  (reverse out))
(defun dbkt-near (a b tol) (< (abs (- a b)) tol))
(defun dbkt-z0 (e) (if (= (cdr (assoc 0 (entget e))) "LWPOLYLINE") (cdr (assoc 38 (entget e))) (caddr (vlax-curve-getStartPoint e))))
(defun dbkt-pts (e / ed out)
  (setq ed (entget e))
  (foreach it ed (if (= (car it) 10) (setq out (cons (cdr it) out))))
  (reverse out))

(defun c:DBKTEST ( / conduits elbows risers spacers env tags recs pl runs rd ok s bom stmts orig types n e pts z
                     f2 tagset codes ss nmed nfit cnt fits elbrec adrec sprec strec e1 lst mn mx)
  (setq *DBKT-PASS* 0 *DBKT-FAIL* nil)
  (setq *DBKT-F* (open *DBKT-OUT* "w"))
  (dbkt-w (strcat "MEDDuctbank test  " (menucmd "M=$(edtime,$(getvar,date),YYYY-MO-DD HH:MM)") "  " *DBK-VERSION*))
  (setq conduits (dbkt-ents "CONDUIT") elbows (dbkt-ents "ELBOW") risers (dbkt-ents "RISER") spacers (dbkt-ents "SPACER")
        env (car (dbkt-ents "ENVELOPE")))
  ;; MED_CONDUIT entities in the drawing (everything the BOM sees as conduit)
  (setq ss (ssget "_X" '((-3 ("MED_CONDUIT")))) nmed (if ss (sslength ss) 0))
  (setq tagset nil n 0)
  (repeat nmed (setq tagset (cons (nth 1 (xdataget (ssname ss n) "MED_CONDUIT")) tagset) n (1+ n)))
  (setq tagset (dbk-uniq tagset))
  (dbkt-w (strcat "MED_CONDUIT entities: " (itoa nmed) " (" (itoa (length conduits)) " runs + " (itoa (length risers)) " risers), distinct tags: "
                  (itoa (length tagset)) " " (vl-princ-to-string (vl-sort tagset '<))))
  (dbkt-check "8 conduit positions (distinct tags)" (= (length tagset) (* *DBKT-ROWS* *DBKT-COLS*)) (itoa (length tagset)))
  (dbkt-check "reference conduit out of BOM" (not (member *DBKT-REFTAG* tagset)) *DBKT-REFTAG*)
  (dbkt-check "every MED_CONDUIT is a bank member" (= nmed (+ (length conduits) (length risers))) "")
  (dbkt-w (strcat "Elbow segments: " (itoa (length elbows)) "  spacer stations: " (itoa (length spacers))))
  (dbkt-check "MED_CONDUIT segments = expected" (= nmed *DBKT-SEGS*) (strcat (itoa nmed) " vs " (itoa *DBKT-SEGS*)))
  (dbkt-check "elbow segments = expected" (= (length elbows) *DBKT-ELBOWS*) (strcat (itoa (length elbows)) " vs " (itoa *DBKT-ELBOWS*)))
;; elbow records. Plan bends: coated RGS elbow + 2 PVC adapters. Stub elbows: elbow (coated
  ;; 160-162 or plain RGS 89/90/91/166) + PVC adapter + coupling (173 coated / 8 RGS) [+ 174 wrap]
  (if (not *DBKT-STUBCODE*) (setq *DBKT-STUBCODE* 2))
  (setq ok T fits nil)
  (foreach e elbows
    (setq recs (cdr (xdataget e "MED_FITTING")) codes nil n 0)
    (repeat (/ (length recs) 6) (setq codes (append codes (list (nth (+ 2 (* 6 n)) recs))) n (1+ n)))
    (setq fits (cons codes fits))
    (if (wcmatch (dbk-xdval e "PART") "BEND*,VBEND*")
      (if (not (and (= (length codes) 3) (member (car codes) '(160 161 162 163 164 165 175 176 177 178 179 180 181 182 183))
                    (= (cadr codes) _DBKADAPTER) (= (caddr codes) _DBKADAPTER)))
        (setq ok nil))
      (if (not (and (member (car codes) (if (= (dbk-xdval e "ANG") "45.00")
                                          (if (= *DBKT-STUBCODE* 1) '(167 168 169) '(163 164 165))
                                          (if (= *DBKT-STUBCODE* 1) '(89 90 91 166) '(160 161 162))))
                    (= (cadr codes) _DBKADAPTER) (= (caddr codes) (if (= *DBKT-STUBCODE* 1) 8 173))
                    (= (length codes) (if *DBKT-WRAP* 4 3))
                    (or (not *DBKT-WRAP*) (= (cadddr codes) 174))))
        (setq ok nil)))
    (if (not (and (dbk-xdval e "OD") (> (atof (dbk-xdval e "OD")) 0.0))) (setq ok nil)))
  (dbkt-w (strcat "Elbow fitting code sets: " (vl-princ-to-string (dbk-uniq fits))))
  (dbkt-check (strcat "elbow records (plan: coated elbow + 2 adapters; stub: "
                      (if (= *DBKT-STUBCODE* 1) "RGS elbow + adapter + RGS coupling" "coated elbow + adapter + coated coupling")
                      (if *DBKT-WRAP* " + wrap" "") ") and OD= on every elbow") ok "")
  (setq ok (and risers (vl-every '(lambda (e) (= (nth 3 (xdataget e "MED_CONDUIT")) *DBKT-STUBCODE*)) risers)))
  (dbkt-check (strcat "risers are code " (itoa *DBKT-STUBCODE*)) ok (itoa (length risers)))
  (setq n (length (vl-remove-if-not '(lambda (e) (= (dbk-xdval e "NOTE") "WRAP")) (dbkt-ents "TEXT"))))
  (dbkt-check "WRAP notes" (= n (if *DBKT-WRAP* (length risers) 0)) (itoa n))
  ;; 3D model on <prefix>Ductbank
  (setq lst (dbkt-ents "ENV3D") e1 (dbkt-ents "SPACER3D"))
  (dbkt-w (strcat "3D model: " (itoa (length lst)) " envelope solid(s), " (itoa (length e1)) " spacer solid(s) on "
                  (vl-princ-to-string (dbk-uniq (mapcar '(lambda (e) (cdr (assoc 8 (entget e)))) (append lst e1))))))
  (dbkt-check "3D envelope: one 3DSOLID on 3DMEDModel-Ductbank"
              (and (= (length lst) 1) (= (cdr (assoc 0 (entget (car lst)))) "3DSOLID") (= (cdr (assoc 8 (entget (car lst)))) (dbk-model-layer))) "")
  (dbkt-check "3D spacer stations: one 3DSOLID per station"
              (and (= (length e1) *DBKT-STATIONS*) (vl-every '(lambda (e) (= (cdr (assoc 0 (entget e))) "3DSOLID")) e1)) (itoa (length e1)))
  (setq ss (ssget "_X" (list (cons 8 (dbk-model-layer)))))
  (dbkt-check "nothing else on the 3D model layer" (= (if ss (sslength ss) 0) (+ (length lst) (length e1))) (itoa (if ss (sslength ss) 0)))
  ;; stub-up encasement (turn-up): unioned into the one envelope solid, plan outline per end
  (if (not *DBKT-TURNUPS*) (setq *DBKT-TURNUPS* 0))
  (setq e (car lst) n (if e (atoi (cond ((dbk-xdval e "TURNUPS")) ("0"))) -1))
  (dbkt-check (strcat "3D envelope includes " (itoa *DBKT-TURNUPS*) " stub-up turn-up(s) (unioned, one solid)") (= n *DBKT-TURNUPS*) (itoa n))
  (setq lst (dbkt-ents "TURNUP"))
  (dbkt-check "turn-up plan outlines (MED_DBENVELOPE, one per stub-up end)"
              (and (= (length lst) *DBKT-TURNUPS*) (vl-every '(lambda (x) (= (cdr (assoc 8 (entget x))) "MED_DBENVELOPE")) lst)) (itoa (length lst)))
  (if (and *DBKT-ENCZ* lst)
    (dbkt-check (strcat "turn-up top EL = " (rtos *DBKT-ENCZ* 2 2))
                (vl-every '(lambda (x) (dbkt-near (cdr (assoc 38 (entget x))) *DBKT-ENCZ* 0.01)) lst)
                (vl-princ-to-string (mapcar '(lambda (x) (cdr (assoc 38 (entget x)))) lst))))
  (if (and e (> *DBKT-TURNUPS* 0))
    (progn
      ;; accoreconsole has no ActiveX (no bounding box): check the solid's turn-up record; full AutoCAD
      ;; (MEDMAKE3D run) checks the real bounding box
      (setq mx (vl-catch-all-apply '(lambda (/ o a b) (setq o (vlax-ename->vla-object e)) (vla-getboundingbox o 'a 'b) (vlax-safearray->list b))))
      (if (not (vl-catch-all-error-p mx))
        (progn (dbkt-w (strcat "3D envelope bbox top Z " (rtos (caddr mx) 2 3)))
               (if *DBKT-ENCZ* (dbkt-check "3D envelope bbox reaches the turn-up top" (dbkt-near (caddr mx) *DBKT-ENCZ* 0.05) (rtos (caddr mx) 2 3)))))
      (setq mn (mapcar '(lambda (k) (cond ((dbk-xdval e k)) (""))) '("ENCZA" "ENCZB")))
      (dbkt-w (strcat "3D envelope turn-up record ENCZA/ENCZB " (vl-princ-to-string mn)))
      (if *DBKT-ENCZ* (dbkt-check "3D envelope turn-up record = turn-up top" (vl-every '(lambda (v) (and (/= v "") (dbkt-near (atof v) *DBKT-ENCZ* 0.01))) mn) ""))))
  (setq n (length (vl-remove-if-not '(lambda (x) (= (dbk-xdval x "NOTE") "TURNUP")) (dbkt-ents "TEXT"))))
  (dbkt-check "turn-up plan notes" (= n *DBKT-TURNUPS*) (itoa n))
  ;; reference route
  (setq e (car (dbkt-ents "REF")))
  (dbkt-check "reference route on MED_DBREF" (and e (= (cdr (assoc 8 (entget e))) "MED_DBREF")) "")
  (if *DBKT-PLAIN*
    (dbkt-check "plain reference: REFPLAIN=1, no MED_CONDUIT data" (and e (= (dbk-xdval e "REFPLAIN") "1") (null (xdataget e "MED_CONDUIT"))) ""))
  ;; dialog spec round trip
  (setq s (dbk-spec-out))
  (setq n (length (vl-remove-if-not '(lambda (l) (wcmatch l "POS=*")) (dbk-split s "\n"))))
  (dbkt-check "dialog spec has every position" (= n (* *DBKT-ROWS* *DBKT-COLS*)) (itoa n))
  (if *DBKT-SPEC* (progn (setq f2 (open *DBKT-SPEC* "w")) (write-line s f2) (close f2)))
  ;; per position geometry
  (setq pl (dbk-get *DBK* "PL"))
  (foreach p (vl-sort pl '(lambda (a b) (< (dbk-get a "POS") (dbk-get b "POS"))))
    (setq runs (vl-remove-if-not '(lambda (e) (= (dbk-xdval e "POS") (dbk-get p "POS"))) conduits))
    (setq z (dbkt-z0 (car runs)))
    (setq lst nil)
    (foreach e (vl-sort runs '(lambda (a b) (< (dbk-xdval a "PART") (dbk-xdval b "PART"))))
      (setq lst (cons (strcat (dbk-xdval e "PART") " " (vl-princ-to-string (mapcar '(lambda (q) (list (atof (rtos (car q) 2 3)) (atof (rtos (cadr q) 2 3)))) (dbkt-pts e)))) lst)))
    (dbkt-w (strcat "  " (dbk-get p "POS") " tag " (dbk-tag p) " size " (rtos (dbk-get p "SIZE") 2 2) " code " (itoa (dbk-get p "CODE"))
                    " OD " (rtos (dbk-get p "OD") 2 3) " tier " (itoa (dbk-get p "TIER")) " lat(trunk) " (dbk-r2 (* (dbk-get *DBKS* "SGN") (dbk-get p "RELT")))
                    " lat(stub) " (dbk-r2 (* (dbk-get *DBKS* "SGN") (dbk-get p "RELS"))) " along " (dbk-r2 (dbk-get p "ALONG"))
                    " CL elev " (dbk-r2 z) " Rstub " (rtos (dbk-get p "RV") 2 0) " Rplan " (vl-princ-to-string (dbk-get p "RP"))))
    (foreach l (reverse lst) (dbkt-w (strcat "      " l))))
  ;; expected trunk positions from the spacer part
  (setq ok T)
  (foreach p pl
    (if (not (dbkt-near (* (dbk-get *DBKS* "SGN") (dbk-get p "RELT")) (* (- (dbk-get p "COL") 1) (dbk-get *DBKS* "PITCHH")) 1e-6)) (setq ok nil))
    (if (not (dbkt-near (* (dbk-get *DBKS* "SGN") (dbk-get p "RELS")) (* (- (dbk-get p "COL") 1) *DBKT-SX*) 1e-6)) (setq ok nil)))
  (dbkt-check "trunk at spacer pitch, stub-ups at stub pitch" ok (strcat "pitch " (dbk-r2 (dbk-get *DBKS* "PITCHH")) " / stub " (dbk-r2 *DBKT-SX*)))
  (setq e1 (car (vl-remove-if-not '(lambda (e) (and (= (dbk-xdval e "POS") (dbk-get *DBK* "REFPOS")) (= (dbk-xdval e "PART") "RUN1"))) conduits)))
  (dbkt-check "reference position on the drawn reference centerline elevation" (dbkt-near (dbkt-z0 e1) (dbk-get *DBK* "ZREF") 1e-6) "")
  ;; envelope
  (dbkt-check "envelope present with bank record" (and env (dbk-xdval env "WT")) "")
  (if env
    (progn
      (dbkt-w (strcat "Envelope: trunk W " (dbk-xdval env "WT") " stub W " (dbk-xdval env "WS") " H " (dbk-xdval env "HT")
                      " top EL " (dbk-xdval env "TOPZ") " bottom EL " (dbk-xdval env "BOTZ") "  member handles " (itoa (length (dbk-xdhandles env)))
                      "  outline vertices " (itoa (length (dbkt-pts env))) "  area " (rtos (vlax-curve-getArea env) 2 1)))
      (dbkt-check "envelope W = expected" (dbkt-near (atof (dbk-xdval env "WT")) *DBKT-WT* 0.005) (strcat (dbk-xdval env "WT") " vs " (rtos *DBKT-WT* 2 4)))
      (dbkt-check "envelope H = expected" (dbkt-near (atof (dbk-xdval env "HT")) *DBKT-HT* 0.005) (strcat (dbk-xdval env "HT") " vs " (rtos *DBKT-HT* 2 4)))
      ;; every conduit vertex inside the plan outline (2D)
      (setq ok T)
      (foreach e (append conduits elbows)
        (foreach q (dbkt-pts e)
          (if (and (= (cdr (assoc 0 (entget e))) "LWPOLYLINE") (equal (cdr (assoc 210 (entget e))) '(0.0 0.0 1.0) 1e-9))
            (if (not (dbkt-inside env q)) (setq ok nil)))))
      (dbkt-check "all plan conduit vertices inside the envelope outline" ok "")
      (dbkt-bend-cover env elbows)))
  (dbkt-check "spacer stations = expected" (= (length spacers) *DBKT-STATIONS*) (strcat (itoa (length spacers)) " vs " (itoa *DBKT-STATIONS*)))
  ;; BOM: capture statements
  (if (not (dbk-doc)) (progn (setq *DBKT-POLYLEN* polylen) (defun polylen (e) (dbk-curvelen e))))
  (setq *DBKT-ORIG* MEDProcessSQLStatement stmts nil)
  (setq *DBKT-STMTS* nil)
  (defun MEDProcessSQLStatement (q) (if (wcmatch (strcase q) "SELECT*") (*DBKT-ORIG* q) (progn (setq *DBKT-STMTS* (cons q *DBKT-STMTS*)) nil)))
  (C:BOM)
  (setq MEDProcessSQLStatement *DBKT-ORIG*)
  (setq stmts (reverse *DBKT-STMTS*))
  (setq types nil)
  (foreach q stmts
    (if (wcmatch q "INSERT INTO MEDProject*")
      (progn
        (setq f2 (dbk-csv-split (substr q (+ 2 (vl-string-search "(" q)))))
        ;; ('TYPE','TAG',RTAG,QTY,SIZE,ALT,DPTH,CODE,...)
        (setq s (strcat (vl-string-trim "'" (nth 0 f2)) " code " (rtos (atof (nth 7 f2)) 2 0) " size " (rtos (atof (nth 4 f2)) 2 2)))
        (if (setq n (assoc s types))
          (setq types (subst (list s (1+ (cadr n)) (+ (caddr n) (atof (nth 3 f2)))) n types))
          (setq types (cons (list s 1 (atof (nth 3 f2))) types))))))
  (dbkt-w (strcat "BOM (captured, not written): " (itoa (length stmts)) " statements"))
  (foreach t1 (vl-sort types '(lambda (a b) (< (car a) (car b))))
    (dbkt-w (strcat "  " (car t1) ": rows " (itoa (cadr t1)) ", qty " (rtos (caddr t1) 2 2)
                    (if (wcmatch (car t1) "CONDUIT*") (strcat " in (" (rtos (/ (caddr t1) 12.0) 2 2) " ft)") ""))))
  (dbkt-check "BOM picks up the bank conduits, elbows, adapters, spacers, straps"
              (and (vl-some '(lambda (x) (wcmatch (car x) "CONDUIT code 3*")) types)
                   (vl-some '(lambda (x) (wcmatch (car x) "FITTING code 16#*")) types)
                   (vl-some '(lambda (x) (wcmatch (car x) "FITTING code 170*")) types)
                   (vl-some '(lambda (x) (wcmatch (car x) "FITTING code 52#*")) types)
                   (vl-some '(lambda (x) (wcmatch (car x) "FITTING code 570*")) types)) "")
  ;; MEDLIST text for one run and one elbow (descriptions come from MEDType)
  (foreach e (list (car conduits) (car elbows) (car spacers))
    (if e
      (progn
        (dbkt-w (strcat "MEDLIST " (dbk-xdval e "ROLE") " " (cond ((dbk-xdval e "POS")) ((dbk-xdval e "STATION")) ("")) ":"))
        (foreach app (xd_apps e)
          (setq recs (cdr (xdataget e app)) n 0)
          (repeat (/ (length recs) (eval (read (strcat "len" (substr app 4)))))
            (setq lst (vl-catch-all-apply 'ShowMEDListData (list app n recs e)))
            (dbkt-w (strcat "   " (if (vl-catch-all-error-p lst) (strcat "ERROR " (vl-catch-all-error-message lst))
                                      (vl-string-translate "\n" " " (apply 'strcat lst)))))
            (setq n (1+ n)))))))
  (if *DBKT-POLYLEN* (setq polylen *DBKT-POLYLEN* *DBKT-POLYLEN* nil))
  (dbkt-w (strcat (itoa *DBKT-PASS*) " passed, " (itoa (length *DBKT-FAIL*)) " failed"))
  (foreach x (reverse *DBKT-FAIL*) (dbkt-w (strcat "  FAILED: " x)))
  (close *DBKT-F*)
  (princ))

;; ---- concrete cover at the bends (_DBKBENDCONC Chamfer / Sweep)
;; 2D distance point - segment
(defun dbkt-segd (q a b / ab t1 l2)
  (setq ab (mapcar '- b a) l2 (+ (* (car ab) (car ab)) (* (cadr ab) (cadr ab))))
  (setq t1 (if (> l2 1e-12) (max 0.0 (min 1.0 (/ (+ (* (- (car q) (car a)) (car ab)) (* (- (cadr q) (cadr a)) (cadr ab))) l2))) 0.0))
  (distance (list (car q) (cadr q)) (list (+ (car a) (* t1 (car ab))) (+ (cadr a) (* t1 (cadr ab))))))
(defun dbkt-samples (e n / l k out)
  (setq l (vlax-curve-getDistAtParam e (vlax-curve-getEndParam e)) k 0)
  (repeat (1+ n) (setq out (cons (vlax-curve-getPointAtDist e (* l (/ (float k) n))) out) k (1+ k)))
  out)
;; plan bends: elbow surface to the envelope outline >= side cover; stub elbows: elbow surface to
;; the turn-up faces (back edge + end face above the trunk top, trunk top face beyond) >= cover
(defun dbkt-cross (a b) (- (* (car a) (cadr b)) (* (cadr a) (car b))))
(defun dbkt-bend-cover (env elbows / wmin vx chs k a b c pc m dnom dact dch nch p zenv covreq od q d dmin nb bulges e end fr prof top face pts segs s z sp
                                     dstub covstub n)
  (setq zenv (cdr (assoc 38 (entget env))) covreq (min (atof (dbk-xdval env "COVL")) (atof (dbk-xdval env "COVR")))
        dmin nil nb 0 nch 0)
  (setq bulges (vl-remove-if '(lambda (x) (or (/= (car x) 42) (< (abs (cdr x)) 1e-9))) (entget env)))
  (dbkt-w (strcat "Concrete at bends: " (cond ((dbk-xdval env "BENDCONC")) ("?")) ", outline arcs " (itoa (length bulges))))
  (if *DBK-CORNERS*
    (dbkt-check (strcat "plan outline " (if (dbk-chamfer-p) "has no arcs (chamfered bends)" "has the swept bend arcs"))
                (if (dbk-chamfer-p) (null bulges) (> (length bulges) 0)) (itoa (length bulges))))
  (dbkt-check "BENDCONC stored on the bank record" (= (dbk-xdval env "BENDCONC") (dbk-bendstr)) (vl-princ-to-string (dbk-xdval env "BENDCONC")))
  ;; outer chamfer segments: near a bend, not parallel to a route leg, outside the turn (bank centerline)
  (setq vx (mapcar '(lambda (q) (list (car q) (cadr q))) (dbkt-pts env)) chs nil k 0)
  (if (dbk-chamfer-p)
    (while (< k (length vx))
      (setq a (nth k vx) b (nth (rem (1+ k) (length vx)) vx))
      (if (and (> (distance a b) 1e-6)
               (vl-every '(lambda (sg) (> (abs (dbkt-cross (dbk-unit (mapcar '- b a)) (nth 2 sg))) 0.01)) *DBK-SEGS*))
        (foreach c *DBK-CORNERS*
          (setq pc (dbk-v+ (list (car (nth 0 c)) (cadr (nth 0 c))) (dbk-v* (nth 7 c) (/ (+ (dbk-get *DBKS* "LEXT") (dbk-get *DBKS* "REXT")) 2.0)))
                m (dbk-v* (mapcar '+ a b) 0.5))
          (if (and (< (distance m pc) (+ 60.0 (dbk-get *DBKS* "WT")))
                   (< (* (dbkt-cross (nth 1 c) (nth 2 c)) (dbkt-cross (nth 1 c) (mapcar '- m pc))) 0.0))
            (setq chs (cons k chs)))))
      (setq k (1+ k))))
  (setq dnom nil dact nil dch nil)
  (foreach e elbows
    (if (wcmatch (dbk-xdval e "PART") "BEND*")
      (progn
        (setq od (atof (dbk-xdval e "OD")) nb (1+ nb)
              p (car (vl-remove-if-not '(lambda (x) (= (dbk-get x "POS") (dbk-xdval e "POS"))) (dbk-get *DBK* "PL"))))
        (foreach q (dbkt-samples e 48)
          (setq q (list (car q) (cadr q) zenv) sp (vlax-curve-getClosestPointTo env q)
                d (distance (list (car q) (cadr q)) (list (car sp) (cadr sp))))
          (if (not (dbkt-inside env q)) (setq d (- d)))
          ;; envelope design OD (the position OD) over the whole elbow
          (if (or (null dnom) (< (- d (/ (dbk-get p "OD") 2.0)) dnom))
            (setq dnom (- d (/ (dbk-get p "OD") 2.0)) wmin (strcat (dbk-xdval e "POS") " " (dbk-xdval e "PART") " at " (rtos (car q) 2 2) "," (rtos (cadr q) 2 2))))
          (if (or (null dact) (< (- d (/ od 2.0)) dact)) (setq dact (- d (/ od 2.0))))
          ;; primary conduit OD where the nearest envelope face is an outside chamfer (cover is sized
          ;; off the primary conduit OD only, no coating allowance: Clint, Oct 7)
          (if (member (fix (vlax-curve-getParamAtPoint env sp)) chs)
            (if (or (null dch) (< (- d (/ (dbk-get p "OD") 2.0)) dch)) (setq dch (- d (/ (dbk-get p "OD") 2.0)) nch (1+ nch))  (setq nch (1+ nch))))))))
  (if (> nb 0)
    (progn
      (dbkt-check (strcat "plan bend cover: elbow (position OD) to envelope face >= side cover " (rtos covreq 2 2) " (" (itoa nb) " elbows x 49 samples)")
                  (>= dnom (- covreq 0.005)) (strcat "min " (rtos dnom 2 3) " (" wmin ")"))
      (if (dbk-chamfer-p)
        (dbkt-check (strcat "outside chamfer cover: elbow (primary OD) to chamfer face >= " (rtos covreq 2 2) " (" (itoa (length chs)) " chamfer faces, " (itoa nch) " samples)")
                    (and dch (>= dch (- covreq 0.005))) (if dch (strcat "min " (rtos dch 2 3)) "no samples")))
      (dbkt-w (strcat "  info only: the coated elbow's own OD to the nearest envelope face, min " (rtos dact 2 3)
                      " (cover is sized off the primary conduit OD, no coating allowance)"))))
  ;; stub elbows vs the turn-up profile
  (setq dstub nil n 0 covstub (min _DBKCOVEREND (atof (dbk-xdval env "COVT"))))
  (foreach end '("A" "B")
    (if (setq z (dbk-get *DBKS* (strcat "ENCZ" end)))
      (progn
        (dbk-tu-set end z)
        (setq top (+ (dbk-get *DBKS* "TOP") *DBK-TUDZ*))
        (setq fr (dbk-tu-frame end) prof (dbk-tu-profile z) face (dbk-tu-face))
        ;; real faces: profile edges above the trunk top except the top edge, plus the trunk top beyond
        (setq segs nil pts prof)
        (while (cdr pts)
          (if (and (>= (min (cadr (car pts)) (cadr (cadr pts))) (- top 1e-6))
                   (not (and (dbkt-near (cadr (car pts)) z 1e-6) (dbkt-near (cadr (cadr pts)) z 1e-6))))
            (setq segs (cons (list (car pts) (cadr pts)) segs)))
          (setq pts (cdr pts)))
        (setq segs (cons (list (list (dbk-tu-back top) top) (list (+ (dbk-tu-back top) 1000.0) top)) segs))
        ;; the back edge crosses the trunk top inside a profile edge: add its upper part
        (setq pts prof)
        (while (cdr pts)
          (if (and (< (cadr (cadr pts)) top) (> (cadr (car pts)) top))
            (setq segs (cons (list (car pts) (list (dbk-tu-back top) top)) segs)))
          (setq pts (cdr pts)))
        (foreach e (append elbows (if (= (dbk-get *DBKS* (strcat "ANG" end)) 45) (dbkt-ents "RISER")))
          (if (member (dbk-xdval e "PART") (list (strcat "STUB" end) (strcat "RISER" end)))
            (progn
              ;; cover on the primary conduit OD (standing rule, 90 and 45 deg ends)
              (setq od (dbk-get (dbk-findpos (dbk-get *DBK* "PL") (dbk-xdval e "POS")) "OD")
                    n (1+ n))
              (foreach q (dbkt-samples e 48)
                (setq s (+ (* (- (car q) (car (car fr))) (car (cadr fr))) (* (- (cadr q) (cadr (car fr))) (cadr (cadr fr)))))
                (if (and (> (caddr q) (- top (/ od 2.0) covstub)) (< (caddr q) (- z 1e-6)))
                  (progn
                    (setq d (- (apply 'min (mapcar '(lambda (sg) (dbkt-segd (list s (caddr q)) (car sg) (cadr sg))) segs)) (/ od 2.0)))
                    (if (or (> s (dbk-tu-back (caddr q))) (< s (dbk-tu-front (caddr q)))) (setq d (- d)))
                    (if (or (null dstub) (< d dstub)) (setq dstub d)))))))))))
  (if dstub
    (dbkt-check (strcat "turn-up cover: stub elbow / riser (primary OD) to turn-up face >= " (rtos covstub 2 2) " (" (itoa n) " stub elbows / 45 deg risers, " (dbk-bendstr) ")")
                (>= dstub (- covstub 0.005)) (strcat "min " (rtos dstub 2 3))))
  (dbkt-levelcut env)
  (princ))
;; MVP4c (Clint, Oct 7): the turn-up top is a level cut below the riser ends; 3D layer transparency
(defun dbkt-levelcut (env / pct end z prof ang zmax n rlow e q od s2 p se r zc w ex ez df db zo zi c1 c2 top proj)
  ;; the bank's own riser projection (the record; DBEDIT must have kept it)
  (setq proj (atof (cond ((dbk-xdval env "RISERPROJ")) ("0"))))
  (if (tblsearch "LAYER" (dbk-model-layer))
    (progn
      (setq pct (dbk-trans-pct (dbk-model-layer)))
      (dbkt-check (strcat "3D model layer " (dbk-model-layer) " transparency " (itoa (cond (*DBKT-LAYTRANS*) (75))) "%")
                  (= pct (cond (*DBKT-LAYTRANS*) (75))) (itoa pct))))
  (dbkt-check (strcat "riser projection on the bank record = " (rtos (cond (*DBKT-PROJ*) (4.0)) 2 2))
              (dbkt-near (atof (cond ((dbk-xdval env "RISERPROJ")) ("-1"))) (cond (*DBKT-PROJ*) (4.0)) 1e-4)
              (vl-princ-to-string (dbk-xdval env "RISERPROJ")))
  (foreach end '("A" "B")
    (if (setq z (dbk-get *DBKS* (strcat "ENCZ" end)))
      (progn
        (dbk-tu-set end z)
        (setq prof (dbk-tu-profile z) ang (dbk-tu-ang) zmax (apply 'max (mapcar 'cadr prof)) n 0
              top (+ (dbk-get *DBKS* "TOP") *DBK-TUDZ*))
        (foreach q prof (if (dbkt-near (cadr q) z 1e-6) (setq n (1+ n))))
        (dbkt-check (strcat "end " end " (" (itoa ang) " deg) turn-up top: one level cut at EL " (rtos z 2 2) ", nothing above it")
                    (and (dbkt-near zmax z 1e-6) (= n 2)) (strcat "top " (rtos zmax 2 4) ", " (itoa n) " vertices at the cut"))
        ;; low edge of the riser ends (45 deg: the slanted end, top - OD/2 x sin 45; primary OD)
        (setq rlow nil)
        (foreach e (dbkt-ents "RISER")
          (if (= (dbk-xdval e "PART") (strcat "RISER" end))
            (progn
              (setq od (dbk-get (dbk-findpos (dbk-get *DBK* "PL") (dbk-xdval e "POS")) "OD")
                    q (- (max (caddr (vlax-curve-getStartPoint e)) (caddr (vlax-curve-getEndPoint e)))
                         (if (= ang 45) (* 0.5 od (sqrt 0.5)) 0.0)))
              (if (or (null rlow) (< q rlow)) (setq rlow q)))))
        (if rlow
          (progn
            (dbkt-check (strcat "end " end " risers project >= " (rtos proj 2 2) "\" above the level cut (riser ends' low edge EL " (rtos rlow 2 2) ")")
                        (>= (- rlow z) (- proj 0.005)) (rtos (- rlow z) 2 3))
            ;; Top (both angles) and Auto at a 45 deg end (MVP4d, Clint) run up to the limit
            (if (or (= (dbk-encval (dbk-get *DBK* "ENCH")) "Top") (and (= ang 45) (= (dbk-encval (dbk-get *DBK* "ENCH")) "Auto")))
              (dbkt-check (strcat "end " end " encasement " (dbk-encstr (dbk-encval (dbk-get *DBK* "ENCH"))) (if (= ang 45) " (45 deg)" "") ": cut the projection below the riser ends")
                          (dbkt-near (- rlow z) proj 0.01) (rtos (- rlow z) 2 3)))))
        ;; 45 deg: the cut's corners sit on the outer / inner cover lines of the risers (no cap past the conduit ends)
        (if (= ang 45)
          (progn
            (setq s2 (sqrt 0.5) df nil db nil zo nil zi nil)
            (foreach p (dbk-get *DBK* "PL")
              (setq se (dbk-tu-se p) r (dbk-get p "RV") zc (dbk-tu-zc p) w (+ (/ (dbk-get p "OD") 2.0) _DBKCOVEREND)
                    ex (- se (* r s2)) ez (+ zc (* r (- 1.0 s2))))
              (setq c1 (+ (* (+ (- (dbk-tu-front z) ex) (- z ez)) s2) w)    ; outer corner: 0 on the outer cover line
                    c2 (- w (* (+ (- (dbk-tu-back z) ex) (- z ez)) s2)))    ; inner corner: 0 on the inner cover line
              ;; the corner sits on the outermost / innermost riser's line (0) and outside every other one (< 0)
              (if (or (null df) (> c1 df)) (setq df c1))
              (if (or (null db) (> c2 db)) (setq db c2))
              (setq q (- ez (* w s2))) (if (or (null zo) (> q zo)) (setq zo q))
              (setq q (+ ez (* w s2))) (if (or (null zi) (> q zi)) (setq zi q)))
            (if (>= z (- zo 1e-6))
              (dbkt-check (strcat "end " end " 45 deg turn-up: outer corner of the cut on the risers' outer cover line (no cap past the conduit ends)")
                          (dbkt-near df 0.0 0.02) (rtos df 2 3)))
            (if (>= z (- zi 1e-6))
              (dbkt-check (strcat "end " end " 45 deg turn-up: inner corner of the cut on the risers' inner cover line")
                          (dbkt-near db 0.0 0.02) (rtos db 2 3))
              (dbkt-w (strcat "  end " end ": cut EL " (rtos z 2 2) " is inside the 45 deg elbow sweep (inner corner on the elbow's cover chord)")))))))))
;; pre-existing 3D model layer (*DBKT-LAYPRE* "old" = made by an earlier build, no transparency; "user" = the user set 40 %)
(defun c:DBKTLAYPRE ( / lay xd)
  (setq lay (dbk-model-layer))
  (if (= *DBKT-LAYPRE* "user")
    (progn (regapp "AcCmTransparency")
           (setq xd (list (list -3 (list "AcCmTransparency" (cons 1071 (+ 33554432 (fix (/ (* 255.0 60) 100.0))))))))))
  (if (not (tblsearch "LAYER" lay))
    (entmake (append (list '(0 . "LAYER") '(100 . "AcDbSymbolTableRecord") '(100 . "AcDbLayerTableRecord")
                           (cons 2 lay) '(70 . 0) '(62 . 8) '(6 . "Continuous") '(290 . 0))
                     xd)))
  (princ (strcat "\n[T] pre-made layer " lay " (" *DBKT-LAYPRE* "), transparency " (itoa (dbk-trans-pct lay)) "%"))
  (princ))

;; point in closed LWPOLYLINE (ray casting on a densified outline: arcs sampled)
(defun dbkt-inside (e q / obj n i pts p1 p2 c k)
  (setq n (fix (vlax-curve-getEndParam e)) i 0.0 pts nil)
  (while (< i n) (setq pts (cons (vlax-curve-getPointAtParam e i) pts) i (+ i 0.125)))
  (setq pts (reverse pts) c nil k 0)
  (while (< k (length pts))
    (setq p1 (nth k pts) p2 (nth (rem (1+ k) (length pts)) pts))
    (if (and (/= (> (cadr p1) (cadr q)) (> (cadr p2) (cadr q)))
             (< (car q) (+ (car p1) (/ (* (- (car p2) (car p1)) (- (cadr q) (cadr p1))) (- (cadr p2) (cadr p1))))))
      (setq c (not c)))
    (setq k (1+ k)))
  c)

;; DBLIST / DBDELETE without picking (the test passes the envelope)
(defun c:DBKTLIST ( / old) (setq old dbk-pick) (defun dbk-pick (m) (car (dbkt-ents "ENVELOPE"))) (c:DBLIST) (setq dbk-pick old) (princ))
(defun c:DBKTDEL ( / old) (setq old dbk-pick) (defun dbk-pick (m) (car (dbkt-ents "ENVELOPE"))) (c:DBDELETE) (setq dbk-pick old) (princ))
;; dialog spec for the reference (setup + solve, nothing drawn): docs / dialog screenshot
(defun c:DBKTSPEC ( / f)
  (if (dbk-setup-ref (handent *DBKT-REFH*))
    (progn
      (if *DBKT-SIZE* (dbk-setpos "*" "SIZE" *DBKT-SIZE*))
      (dbk-solve)
      (setq f (open *DBKT-SPEC* "w")) (write-line (dbk-spec-out) f) (close f)
      (princ (strcat "\n[T] spec written: " *DBKT-SPEC*))))
  (princ))

;; plain 3D polyline reference: copy the vertices of the MED reference (handle *DBKT-REFH*) into a
;; new 3DPOLY with no MED data on layer 0, erase the original, and make dbk-pick return the copy
(defun c:DBKTPLAIN ( / src v pts e)
  (setq src (handent *DBKT-REFH*) v (entnext src) pts nil)
  (while (and v (= (cdr (assoc 0 (entget v))) "VERTEX"))
    (if (= 0 (logand 16 (cdr (assoc 70 (entget v))))) (setq pts (cons (cdr (assoc 10 (entget v))) pts)))
    (setq v (entnext v)))
  (setq pts (reverse pts))
  (entmake '((0 . "POLYLINE") (8 . "0") (66 . 1) (10 0.0 0.0 0.0) (70 . 8)))
  (foreach p pts (entmake (list '(0 . "VERTEX") '(8 . "0") (cons 10 p) '(70 . 32))))
  (entmake '((0 . "SEQEND") (8 . "0")))
  (setq e (entlast))   ; the POLYLINE header (entlast returns main entities)
  (entdel src)
  (setq *DBKT-PLAINE* e *DBKT-PLAINH* (cdr (assoc 5 (entget e))))
  (princ (strcat "\n[T] plain 3DPOLY " *DBKT-PLAINH* " with " (itoa (length pts)) " vertices (no xdata: "
                 (vl-princ-to-string (assoc -3 (entget e '("*")))) "); source " *DBKT-REFH* " erased"))
  (setq *DBKT-OLDPICK* dbk-pick)
  (defun dbk-pick (m) *DBKT-PLAINE*)
  (princ))
(defun c:DBKTPICKRESET () (if *DBKT-OLDPICK* (setq dbk-pick *DBKT-OLDPICK* *DBKT-OLDPICK* nil)) (princ))

;; DBEDIT round trip: snapshot, -DBEDIT (scripted answers), check
(defun dbkt-bank-all (bank / ss i e out)
  (setq ss (ssget "_X" '((-3 ("DBANK_DATA")))) i 0)
  (if ss (repeat (sslength ss) (setq e (ssname ss i) i (1+ i)) (if (= (dbk-xdval e "BANK") bank) (setq out (cons e out)))))
  out)
(defun dbkt-all-count ( / ss) (setq ss (ssget "_X")) (if ss (sslength ss) 0))
(defun dbkt-refrun ( / env)
  (setq env (car (dbkt-ents "ENVELOPE")))
  (car (vl-remove-if-not '(lambda (e) (and (= (dbk-xdval e "POS") (dbk-xdval env "REFPOS")) (= (dbk-xdval e "PART") "RUN1"))) (dbkt-ents "CONDUIT"))))
(defun c:DBKTEDITPRE ( / env)
  (setq env (car (dbkt-ents "ENVELOPE")))
  (setq *DBKT-EP0* (car (dbkt-pts (dbkt-refrun))))
  ;; edit the reference route on MED_DBREF (move it 12" east): DBEDIT must rebuild on the edited route
  (if *DBKT-EMOVE* (command "_.MOVE" (car (dbkt-ents "REF")) "" "0,0,0" (strcat (rtos *DBKT-EMOVE* 2 4) ",0,0")))
  (setq *DBKT-EBANK* (dbk-xdval env "BANK")
        *DBKT-EOLD* (mapcar '(lambda (e) (list (cdr (assoc 5 (entget e))) (dbk-xdval e "ROLE"))) (dbkt-bank-all *DBKT-EBANK*))
        *DBKT-EALL* (dbkt-all-count))
  (princ (strcat "\n[T] DBEDIT snapshot: bank " *DBKT-EBANK* ", " (itoa (length *DBKT-EOLD*)) " members, " (itoa *DBKT-EALL*) " entities in the drawing"))
  (princ))
(defun c:DBKTEDIT ( / old) (setq old dbk-pick) (defun dbk-pick (m) (car (dbkt-ents "ENVELOPE"))) (c:-DBEDIT) (setq dbk-pick old) (princ))
(defun c:DBKTEDITCHK ( / env mem hs ok n orphans gone e x tg recs)
  (setq *DBKT-F* (open *DBKT-OUT* "a"))
  (dbkt-w "---- DBEDIT round trip")
  (setq env (car (dbkt-ents "ENVELOPE")) mem (dbkt-bank-all *DBKT-EBANK*))
  (dbkt-check "one bank record after the rebuild, same bank ID" (and env (= (length (dbkt-ents "ENVELOPE")) 1) (= (dbk-xdval env "BANK") *DBKT-EBANK*)) "")
  (setq x (cond (*DBKT-EDROP*) (0)))   ; members an older build had that the rebuild drops (e91df9d BUBs)
  (dbkt-check (if (> x 0) (strcat "member count = old - " (itoa x) " dropped BUBs") "member count unchanged") (= (length mem) (- (length *DBKT-EOLD*) x)) (strcat (itoa (length mem)) " vs " (itoa (length *DBKT-EOLD*))))
  (dbkt-check (if (> x 0) (strcat "drawing entity count = old - " (itoa x) " (no orphans, no duplicates)") "drawing entity count unchanged (no orphans, no duplicates)")
              (= (dbkt-all-count) (- *DBKT-EALL* x)) (strcat (itoa (dbkt-all-count)) " vs " (itoa *DBKT-EALL*)))
  (setq n (length (dbkt-ents "ENV3D")))
  (dbkt-check "one 3D envelope solid (no duplicate)" (= n 1) (itoa n))
  (setq n (length (dbkt-ents "SPACER3D")))
  (dbkt-check "3D spacer solids = stations (no duplicates)" (= n *DBKT-STATIONS*) (itoa n))
  (setq x (ssget "_X" (list '(0 . "3DSOLID") (cons 8 (dbk-model-layer)))))
  (dbkt-check "3DSOLIDs on the model layer = 1 + stations" (= (if x (sslength x) 0) (1+ *DBKT-STATIONS*)) (itoa (if x (sslength x) 0)))
  (setq hs (dbk-xdhandles env) ok T)
  (foreach h hs (if (not (and (handent h) (entget (handent h)))) (setq ok nil)))
  (dbkt-check "every handle in the bank record exists" ok (itoa (length hs)))
  (setq orphans nil)
  (foreach e mem
    (if (not (or (eq e env) (member (cdr (assoc 5 (entget e))) hs) (= (dbk-xdval e "ROLE") "REF"))) (setq orphans (cons (dbk-xdval e "ROLE") orphans))))
  (dbkt-check "no orphan bank entities (all listed in the bank record)" (null orphans) (vl-princ-to-string orphans))
  (setq gone T)
  (foreach o *DBKT-EOLD*
    (setq e (handent (car o)))
    (if (= (cadr o) "REF")
      (if (not (and e (entget e))) (setq gone nil))
      (if (and e (entget e)) (setq gone nil))))
  (dbkt-check "old members erased, reference route kept" gone "")
  (setq ok T n 0)
  (foreach e (append (dbkt-ents "CONDUIT") (dbkt-ents "RISER"))
    (if (= (dbk-xdval e "POS") "A1") (progn (setq n (1+ n)) (if (/= (nth 1 (xdataget e "MED_CONDUIT")) *DBKT-ETAG*) (setq ok nil)))))
  (dbkt-check (strcat "A1 conduits / risers retagged " *DBKT-ETAG*) (and ok (> n 0)) (itoa n))
  (setq ok T n 0)
  (if *DBKT-ESIZE*
    (progn
      (foreach e (append (dbkt-ents "CONDUIT") (dbkt-ents "RISER"))
        (if (= (dbk-xdval e "POS") "B2") (progn (setq n (1+ n)) (if (not (equal (nth 2 (xdataget e "MED_CONDUIT")) *DBKT-ESIZE* 1e-6)) (setq ok nil)))))
      (dbkt-check (strcat "B2 conduits / risers at " (rtos *DBKT-ESIZE* 2 2) "\"") (and ok (> n 0)) (itoa n))))
  (setq ok T n 0)
  (foreach e (append (dbkt-ents "CONDUIT") (dbkt-ents "RISER"))
    (if (not (member (dbk-xdval e "POS") '("A1" "B2"))) (progn (setq n (1+ n)) (if (= (nth 1 (xdataget e "MED_CONDUIT")) *DBKT-ETAG*) (setq ok nil)))))
  (dbkt-check "other positions keep their tags" ok (itoa n))
  (if *DBKT-EMOVE*
    (progn (setq x (car (dbkt-pts (dbkt-refrun))))
           (dbkt-check (strcat "rebuilt on the edited route (reference moved " (rtos *DBKT-EMOVE* 2 2) "\" east)")
                       (and x (dbkt-near (- (car x) (car *DBKT-EP0*)) *DBKT-EMOVE* 0.01) (dbkt-near (cadr x) (cadr *DBKT-EP0*) 0.01))
                       (strcat "REF run start " (vl-princ-to-string *DBKT-EP0*) " -> " (vl-princ-to-string x)))))
  (setq recs (dbk-xdvals env "P"))
  (dbkt-w (strcat "P= records: " (vl-princ-to-string recs)))
  (dbkt-check (if *DBKT-ESIZE* "P= records updated (A1 custom tag, B2 size)" "P= records updated (A1 custom tag)")
              (and (vl-some '(lambda (r / f) (setq f (dbk-split r "|")) (and (= (car f) "A1") (= (nth 1 f) *DBKT-ETAG*) (= (nth 4 f) "C"))) recs)
                   (or (null *DBKT-ESIZE*)
                       (vl-some '(lambda (r / f) (setq f (dbk-split r "|")) (and (= (car f) "B2") (equal (atof (nth 2 f)) *DBKT-ESIZE* 1e-6))) recs))) "")
  (dbkt-w (strcat "Envelope after DBEDIT: W " (dbk-xdval env "WT") " H " (dbk-xdval env "HT") " part " (dbk-xdval env "SPACER")
                  " turn-ups " (cond ((dbk-xdval (car (dbkt-ents "ENV3D")) "TURNUPS")) ("?"))))
  (dbkt-w (if *DBKT-ESIZE* "Concrete cover at the bends after the rebuild (B2 now 4\", R36):" "Concrete cover at the bends after the rebuild:"))
  (dbkt-bend-cover (car (dbkt-ents "ENVELOPE")) (dbkt-ents "ELBOW"))
  (dbkt-w (strcat (itoa *DBKT-PASS*) " passed, " (itoa (length *DBKT-FAIL*)) " failed (cumulative)"))
  (foreach x (reverse *DBKT-FAIL*) (dbkt-w (strcat "  FAILED: " x)))
  (close *DBKT-F*)
  (princ))

;;; ---- MVP4: route profile + 45 deg BUB stub-ups
;; plain 3DPOLY test route from *DBKT-ROUTE* (list of 3D points) on layer 0; dbk-pick returns it
(defun c:DBKTROUTE ( / e)
  (entmake '((0 . "POLYLINE") (8 . "0") (66 . 1) (10 0.0 0.0 0.0) (70 . 8)))
  (foreach p *DBKT-ROUTE* (entmake (list '(0 . "VERTEX") '(8 . "0") (cons 10 (mapcar 'float p)) '(70 . 32))))
  (entmake '((0 . "SEQEND") (8 . "0")))
  (setq e (entlast) *DBKT-PLAINE* e *DBKT-PLAINH* (cdr (assoc 5 (entget e))))
  ;; the sample's MED reference conduit would count in the BOM checks: erase it
  (if (and *DBKT-REFH* (handent *DBKT-REFH*) (entget (handent *DBKT-REFH*))) (entdel (handent *DBKT-REFH*)))
  (princ (strcat "\n[T] test route 3DPOLY " *DBKT-PLAINH* " with " (itoa (length *DBKT-ROUTE*)) " vertices"))
  (setq *DBKT-OLDPICK* dbk-pick)
  (defun dbk-pick (m) *DBKT-PLAINE*)
  (princ))
(defun dbkt-route-path ( / segs) (setq segs *DBK-SEGS*) (cons (car (car segs)) (mapcar 'cadr segs)))
(defun dbkt-3dverts (e / v out)
  (if (= (cdr (assoc 0 (entget e))) "POLYLINE")
    (progn (setq v (entnext e))
           (while (and v (= (cdr (assoc 0 (entget v))) "VERTEX"))
             (if (= 0 (logand 16 (cdr (assoc 70 (entget v))))) (setq out (cons (cdr (assoc 10 (entget v))) out)))
             (setq v (entnext v)))
           (reverse out))
    (list (vlax-curve-getStartPoint e) (vlax-curve-getEndPoint e))))
;; point in polygon ((x y) ...) and distance to its boundary
(defun dbkt-inpoly (q poly / c k p1 p2 n)
  (setq n (length poly) k 0)
  (repeat n
    (setq p1 (nth k poly) p2 (nth (rem (1+ k) n) poly))
    (if (and (/= (> (cadr p1) (cadr q)) (> (cadr p2) (cadr q)))
             (< (car q) (+ (car p1) (/ (* (- (car p2) (car p1)) (- (cadr q) (cadr p1))) (- (cadr p2) (cadr p1))))))
      (setq c (not c)))
    (setq k (1+ k)))
  c)
(defun dbkt-polyd (q poly / n k d m)
  (setq n (length poly) k 0)
  (repeat n (setq d (dbkt-segd q (nth k poly) (nth (rem (1+ k) n) poly))) (if (or (null m) (< d m)) (setq m d)) (setq k (1+ k)))
  m)
(defun c:DBKTPROF ( / vx nf nb st ok els n e codes recs b ang v pos ends fr all p pts q r m d dmin wmin poly path s z covreq
                      bubs stubs c risers rz rp sp stmts types f2 x lst env end tol k)
  (setq *DBKT-F* (open *DBKT-OUT* "a"))
  (dbkt-w "---- route profile / 45 deg stub-ups (DBKTPROF)")
  (setq env (car (dbkt-ents "ENVELOPE")) vx (dbk-get *DBKS* "VX") pos (dbk-get *DBK* "PL"))
  (foreach l (dbk-prof-summary) (dbkt-w (strcat "  " l)))
  (setq nf (length (vl-remove-if-not '(lambda (v) (= (nth 6 v) "FLEX")) vx))
        nb (length (vl-remove-if-not '(lambda (v) (= (nth 6 v) "BEND")) vx)))
  (dbkt-check (strcat "profile: " (itoa *DBKT-NFLEX*) " flex point(s) (no fitting), " (itoa *DBKT-NVB*) " vertical bend(s)")
              (and (= nf *DBKT-NFLEX*) (= nb *DBKT-NVB*)) (strcat (itoa nf) " flex, " (itoa nb) " bends"))
  (setq st (mapcar '(lambda (v) (nth 7 v)) (vl-remove-if-not '(lambda (v) (= (nth 6 v) "BEND")) vx)))
  (dbkt-check "vertical bend stock angles" (equal st *DBKT-VBSTOCK* 1e-6) (vl-princ-to-string st))
  (dbkt-check "bank record: PROFILE / VBENDS / FLEXPTS"
              (and (= (dbk-xdval env "PROFILE") (if (= (+ nf nb) 0) "LEVEL" "GRADE")) (= (dbk-xdval env "VBENDS") (itoa nb)) (= (dbk-xdval env "FLEXPTS") (itoa nf)))
              (strcat (vl-princ-to-string (dbk-xdval env "PROFILE")) " " (vl-princ-to-string (dbk-xdval env "VBENDS")) " " (vl-princ-to-string (dbk-xdval env "FLEXPTS"))))
  ;; vertical bend elbows: count, codes by stock angle + radius, true vertical arcs at the drawn angle
  (setq els (vl-remove-if-not '(lambda (e) (wcmatch (dbk-xdval e "PART") "VBEND*")) (dbkt-ents "ELBOW")) ok T)
  (foreach e els
    (setq recs (cdr (xdataget e "MED_FITTING")) codes (list (nth 2 recs) (nth 8 recs) (nth 14 recs))
          v (nth (1- (atoi (substr (dbk-xdval e "PART") 6))) (vl-remove-if-not '(lambda (v) (= (nth 6 v) "BEND")) vx))
          b (cdr (assoc 42 (entget e))) ang (* 4.0 (atan (abs b)) (/ 180.0 pi)))
    (if (not (and v (= (car codes) (cdr (assoc (atof (dbk-xdval e "RAD")) (cdr (assoc (if (= (nth 7 v) 45.0) 45 (if (= (nth 7 v) 90.0) 90 (nth 7 v))) *DBK-ELBOWS*)))))
                  (= (cadr codes) _DBKADAPTER) (= (caddr codes) _DBKADAPTER)
                  (dbkt-near ang (abs (dbk-deg (nth 5 v))) 0.01) (dbkt-near (atof (dbk-xdval e "ANG")) ang 0.01)
                  (dbkt-near (caddr (cdr (assoc 210 (entget e)))) 0.0 1e-9)))
      (progn (setq ok nil) (dbkt-w (strcat "    bad vertical elbow " (dbk-xdval e "POS") " " (dbk-xdval e "PART") " codes " (vl-princ-to-string codes) " arc " (rtos ang 2 3))))))
  (dbkt-check (strcat "vertical bend elbows: " (itoa (* nb (length pos))) " (bends x positions), stock code by angle + R, + 2 adapters, vertical arc at the drawn angle")
              (and ok (= (length els) (* nb (length pos)))) (strcat (itoa (length els)) " " (vl-princ-to-string (dbk-uniq (mapcar '(lambda (e) (nth 2 (xdataget e "MED_FITTING"))) els)))))
  ;; continuous conduit path per position: every end meets another piece except the free ends
  (setq ok T)
  (foreach p pos
    (setq all (vl-remove-if-not '(lambda (e) (and (= (dbk-xdval e "POS") (dbk-get p "POS")) (member (dbk-xdval e "ROLE") '("CONDUIT" "RISER" "ELBOW"))))
                                (append (dbkt-ents "CONDUIT") (dbkt-ents "RISER") (dbkt-ents "ELBOW"))))
    (setq pts nil)
    (foreach e all (setq pts (cons (vlax-curve-getStartPoint e) (cons (vlax-curve-getEndPoint e) pts))))
    (setq n 0)
    (foreach q pts (if (< (length (vl-remove-if-not '(lambda (x) (< (distance x q) 0.001)) pts)) 2) (setq n (1+ n))))
    (if (/= n *DBKT-FREEENDS*) (progn (setq ok nil) (dbkt-w (strcat "    " (dbk-get p "POS") ": " (itoa n) " free ends")))))
  (dbkt-check (strcat "conduit path continuous per position (" (itoa *DBKT-FREEENDS*) " free ends: riser tops / open ends)") ok "")
  ;; the reference position follows the drawn route elevations (vertices outside the bends)
  (setq path (dbkt-route-path) rp nil)
  (foreach q (dbkt-3dverts (car (dbkt-ents "REF"))) (setq rp (cons (list (dbk-proj-s (dbk-xy q) path) (caddr q)) rp)))
  (setq rp (vl-remove-if '(lambda (q) (or (< (car q) 1e-6) (> (car q) (- (dbk-get *DBKS* "LEN") 1e-6)))) (reverse rp)))
  (setq rp (append (list (list 0.0 (dbk-get *DBK* "ZREF"))) rp (list (list (dbk-get *DBKS* "LEN") (+ (dbk-get *DBK* "ZREF") (dbk-get *DBKS* "DZB"))))))
  (setq ok T dmin 0.0)
  (foreach e (vl-remove-if-not '(lambda (e) (= (dbk-xdval e "POS") (dbk-get *DBK* "REFPOS"))) (dbkt-ents "CONDUIT"))
    (foreach q (dbkt-3dverts e)
      (setq s (dbk-proj-s (dbk-xy q) path) d (abs (- (caddr q) (dbk-prof-z rp s))))
      (if (> d dmin) (setq dmin d))))
  (dbkt-check "reference position runs on the drawn route elevations" (< dmin 0.01) (strcat "max dev " (rtos dmin 2 4)))
  ;; cover to the profile slab (sloped / stepped trunk, 3D envelope)
  (if (setq poly (dbk-get *DBKS* "SLAB"))
    (progn
      (setq covreq (min _DBKCOVERTOP _DBKCOVERBOT) dmin nil n 0)
      (foreach e (vl-remove-if-not '(lambda (e) (or (= (dbk-xdval e "ROLE") "CONDUIT") (wcmatch (dbk-xdval e "PART") "VBEND*,BEND*")))
                                   (append (dbkt-ents "CONDUIT") (dbkt-ents "ELBOW")))
        (setq p (dbk-findpos pos (dbk-xdval e "POS")))
        (foreach q (dbkt-samples e 40)
          (setq s (dbk-proj-s (dbk-xy q) path) x (list s (caddr q)) n (1+ n)
                d (- (dbkt-polyd x poly) (/ (dbk-get p "OD") 2.0)))
          (if (not (dbkt-inpoly x poly)) (setq d (- d)))
          (if (or (null dmin) (< d dmin)) (setq dmin d wmin (strcat (dbk-xdval e "POS") " " (dbk-xdval e "PART") " sta " (rtos s 2 1))))))
      (dbkt-check (strcat "profile envelope: conduit / vertical elbow OD to top / bottom of concrete >= " (rtos covreq 2 2) " (" (itoa n) " samples)")
                  (>= dmin (- covreq 0.005)) (strcat "min " (rtos dmin 2 3) " (" wmin ")"))
      ;; spacer stations: not in a vertical bend, 2D insert at the profile bottom of concrete
      (setq ok T)
      (foreach e (dbkt-ents "SPACER")
        (setq s (atof (dbk-xdval e "STA")))
        (foreach z (dbk-get *DBKS* "VBZ") (if (and (> s (car z)) (< s (cadr z))) (setq ok nil)))
        (if (not (dbkt-near (caddr (cdr (assoc 10 (entget e)))) (+ (dbk-get *DBKS* "BOT") (dbk-dz s)) 0.01)) (setq ok nil)))
      (dbkt-check "spacer stations outside the vertical bends, inserts at the profile bottom of concrete" ok (itoa (length (dbkt-ents "SPACER"))))))
  ;; 45 deg stub-ups: no fitting at the stub-up (Clint, Oct 7): 45 deg stub elbow + 45 deg riser, open riser top
  (setq bubs (dbkt-bubcount))
  (dbkt-check "no BUB fittings at the stub-ups (no ROLE=BUB, no 1bub / DBK_BUB inserts, no DBK_BUB block)" (= bubs 0) (itoa bubs))
  (dbkt-check "bank record ANGA / ANGB, no BUBS key" (and (null (dbk-xdval env "BUBS")) (= (dbk-xdval env "ANGA") (itoa *DBKT-ANGA*)) (= (dbk-xdval env "ANGB") (itoa *DBKT-ANGB*)))
              (strcat (vl-princ-to-string (dbk-xdval env "BUBS")) " " (vl-princ-to-string (dbk-xdval env "ANGA")) " " (vl-princ-to-string (dbk-xdval env "ANGB"))))
  (if (> *DBKT-N45* 0)
    (progn
      (setq ok T n 0)
      (foreach c (dbkt-ents "STUB")
        (setq end (dbk-xdval c "END"))
        (if (= (dbk-get *DBKS* (strcat "ANG" end)) 45)
          (progn
            (setq n (1+ n) q (cdr (assoc 10 (entget c))) z (+ (dbk-get *DBK* (strcat "TOP" end)) 0.0)
                  r (car (vl-remove-if-not '(lambda (x) (and (= (dbk-xdval x "POS") (dbk-xdval c "POS")) (= (dbk-xdval x "PART") (strcat "RISER" end)))) (dbkt-ents "RISER"))))
            (if (not (and (dbkt-near (caddr q) z 1e-6)
                          r (progn (setq pts (dbkt-3dverts r))
                                   (and (dbkt-near (distance (car pts) q) 0.0 0.001)
                                        (dbkt-near (abs (- (caddr (car pts)) (caddr (cadr pts)))) (distance (dbk-xy (car pts)) (dbk-xy (cadr pts))) 0.01)))))
              (progn (setq ok nil) (dbkt-w (strcat "    bad 45 deg stub-up " (dbk-xdval c "POS") " end " end " " (vl-princ-to-string q))))))))
      (dbkt-check (strcat "45 deg risers: " (itoa n) " end open at the stub-up point, top EL (45 deg)") (and ok (= n *DBKT-N45*)) "")
      (setq ok T n 0)
      (foreach e (dbkt-ents "ELBOW")
        (if (and (wcmatch (dbk-xdval e "PART") "STUB*") (= (dbk-get *DBKS* (strcat "ANG" (substr (dbk-xdval e "PART") 5))) 45))
          (progn (setq n (1+ n) recs (cdr (xdataget e "MED_FITTING")) b (cdr (assoc 42 (entget e))))
                 (if (not (and (= (dbk-xdval e "ANG") "45.00") (member (nth 2 recs) (if (= *DBKT-STUBCODE* 1) '(167 168 169) '(163 164 165)))
                               (dbkt-near (* 4.0 (atan (abs b)) (/ 180.0 pi)) 45.0 0.01)))
                   (setq ok nil)))))
      (dbkt-check (strcat "45 deg stub elbows: " (itoa n) " (45 deg arcs, " (if (= *DBKT-STUBCODE* 1) "RGS 167-169" "coated 163-165") ")") (and ok (= n *DBKT-N45*)) "")))
  ;; flags
  (foreach pat *DBKT-FLAGPATS*
    (dbkt-check (strcat "flag: " pat) (vl-some '(lambda (f) (wcmatch f pat)) (dbk-get *DBKS* "FLAGS")) ""))
  (dbkt-check "no solve errors" (null (dbk-get *DBKS* "ERRS")) (vl-princ-to-string (dbk-get *DBKS* "ERRS")))
  ;; BOM codes (captured, not written)
  (if *DBKT-BOMCODES*
    (progn
      (if (not (dbk-doc)) (progn (setq *DBKT-POLYLEN* polylen) (defun polylen (e) (dbk-curvelen e))))
      (setq *DBKT-ORIG* MEDProcessSQLStatement *DBKT-STMTS* nil)
      (defun MEDProcessSQLStatement (q) (if (wcmatch (strcase q) "SELECT*") (*DBKT-ORIG* q) (progn (setq *DBKT-STMTS* (cons q *DBKT-STMTS*)) nil)))
      (C:BOM)
      (setq MEDProcessSQLStatement *DBKT-ORIG* types nil)
      (foreach q (reverse *DBKT-STMTS*)
        (if (wcmatch q "INSERT INTO MEDProject*")
          (progn (setq f2 (dbk-csv-split (substr q (+ 2 (vl-string-search "(" q)))))
                 (if (= (vl-string-trim "'" (nth 0 f2)) "FITTING") (setq types (cons (fix (atof (nth 7 f2))) types))))))
      (if *DBKT-POLYLEN* (setq polylen *DBKT-POLYLEN* *DBKT-POLYLEN* nil))
      (setq types (vl-sort (dbk-uniq types) '<))
      (dbkt-w (strcat "  BOM fitting codes: " (vl-princ-to-string types)))
      (dbkt-check (strcat "BOM has fitting codes " (vl-princ-to-string *DBKT-BOMCODES*)) (vl-every '(lambda (c) (member c types)) *DBKT-BOMCODES*) "")
      (dbkt-check "BOM has no BUB code 94" (not (member 94 types)) "")))
  (dbkt-w (strcat (itoa *DBKT-PASS*) " passed, " (itoa (length *DBKT-FAIL*)) " failed (cumulative)"))
  (foreach x (reverse *DBKT-FAIL*) (dbkt-w (strcat "  FAILED: " x)))
  (close *DBKT-F*)
  (princ))
;; ---- banks built by e91df9d (45 deg stub-ups had Mogul BUB inserts): BUB members left in the drawing
(defun dbkt-bubcount ( / ss i n)
  (setq n 0 ss (ssget "_X" '((-3 ("DBANK_DATA")))) i 0)
  (if ss (repeat (sslength ss) (if (= (dbk-xdval (ssname ss i) "ROLE") "BUB") (setq n (1+ n))) (setq i (1+ i))))
  (if (setq ss (ssget "_X" '((0 . "INSERT") (2 . "DBK_BUB,1BUB")))) (setq n (+ n (sslength ss))))
  (if (tblsearch "BLOCK" "DBK_BUB") (setq n (1+ n)))
  n)
(defun c:DBKTBUBCOUNT () (setq *DBKT-OLDBUBS* (dbkt-bubcount)) (princ (strcat "\n[T] BUB members / inserts / DBK_BUB block: " (itoa *DBKT-OLDBUBS*))) (princ))
;; after loading the current MEDDuctbank.lsp and DBEDIT on the old bank
(defun c:DBKTOLDBUB ( / n)
  (setq *DBKT-F* (open *DBKT-OUT* "a"))
  (dbkt-w "---- old bank (built by e91df9d with BUB fittings)")
  (dbkt-check (strcat "the e91df9d build made BUBs (" (itoa *DBKT-OLDBUBEXP*) " ROLE=BUB DBK_BUB inserts + the DBK_BUB block)") (= *DBKT-OLDBUBS* (1+ (* 2 *DBKT-OLDBUBEXP*))) (itoa *DBKT-OLDBUBS*))
  (setq n (dbkt-bubcount))
  (dbkt-check "afterwards (DBEDIT rebuild or DBDELETE): no BUB inserts, no ROLE=BUB members, DBK_BUB block purged" (= n 0) (itoa n))
  (dbkt-w (strcat (itoa *DBKT-PASS*) " passed, " (itoa (length *DBKT-FAIL*)) " failed (cumulative)"))
  (foreach x (reverse *DBKT-FAIL*) (dbkt-w (strcat "  FAILED: " x)))
  (close *DBKT-F*)
  (princ))
;; after DBDELETE: nothing of the bank left (BUBs included), reference route restored
(defun c:DBKTDELCHK ( / n ref)
  (setq *DBKT-F* (open *DBKT-OUT* "a"))
  (dbkt-w "---- DBDELETE")
  (setq n (length (dbk-bank-ents *DBKT-EBANK*)))
  (dbkt-check (strcat "no entities of bank " *DBKT-EBANK* " left") (= n 0) (itoa n))
  (setq n (dbkt-bubcount))
  (dbkt-check "no BUB inserts / members left, DBK_BUB block purged" (= n 0) (itoa n))
  (setq ref (handent *DBKT-DELREF*))
  (dbkt-check "reference route restored (still in the drawing, no DBANK_DATA)" (and ref (entget ref) (null (dbk-xdval ref "ROLE"))) "")
  (dbkt-w (strcat (itoa *DBKT-PASS*) " passed, " (itoa (length *DBKT-FAIL*)) " failed (cumulative)"))
  (foreach x (reverse *DBKT-FAIL*) (dbkt-w (strcat "  FAILED: " x)))
  (close *DBKT-F*)
  (princ))
(defun c:DBKTDELPRE ( / env)
  (setq env (car (dbkt-ents "ENVELOPE")) *DBKT-EBANK* (dbk-xdval env "BANK")
        *DBKT-DELREF* (cdr (assoc 5 (entget (car (dbkt-ents "REF"))))))
  (princ))
(princ "\nMEDDuctbankTest loaded: DBKTEST DBKTLIST DBKTDEL DBKTSPEC DBKTPLAIN DBKTEDITPRE DBKTEDIT DBKTEDITCHK DBKTROUTE DBKTPROF DBKTBUBCOUNT DBKTOLDBUB DBKTDELPRE DBKTDELCHK")
(princ)
