(princ "\rLoading MEDTag...")
(defun c:sect( / pt1 pt2 val)
    (med_cur_set "C:SECT")
    (setq curatdia (getvar "ATTDIA"))
    (smlayer _MEDTEXT)
    (setq pt1 (getpoint "\nPick first section point"))
    (setvar "orthomode" 1)
    (setq pt2 (getpoint "\nPick second section point" pt1))
    (setq val (getstring "\nEnter section letter <A>: "))
    (setvar "attdia" 0)
    (command "insert" "sect1" pt1 (* 1.0 _SC) "" pt2 )
    (command "insert" "sect" pt1 (* 1.0 _SC) "" "" val)
    (command "copy" "l" "" pt1 pt2)
    (command "insert" "sect2" pt2 (* 1.0 _SC) "" pt1)
    (setvar "ATTDIA" curatdia)
    (med_ret_ok)
	(princ)
)
(defun c:cut( / lay pt1 pt2 val)
   (med_cur_set "C:CUT")
   (setq curatdia (getvar "ATTDIA"))
   (smlayer _MEDTEXT)
   (setq pt1 (getpoint "\nPick first section point"))
   (setvar "orthomode" 1)
   (setq pt2 (getpoint "\nPick second section point" pt1))
   (setq val (getstring "\nEnter section letter : "))
   (setvar "attdia" 0)
   (command "insert" "cut1" pt1 (* 1.0 _SC) "" pt2 )
   (command "insert" "sect" pt1 (* 1.0 _SC) "" "" val)
   (command "copy" "l" "" pt1 pt2)
   (command "insert" "cut2" pt2 (* 1.0 _SC) "" pt1)
   (setvar "ATTDIA" curatdia)
   (med_ret_ok)
)



(defun c:cloud( / clpt clpt1 head hdata bulge en ed)
  (med_cur_set "C:CLOUD")
  (medsmlayer _REVISION)
  (command "pline")
  (setq ptprompt "\nDraw Pline Counter Clockwise to buldge Out or Clockwise for in: "
        conpt (getpoint ptprompt)
  )
  (command conpt)
  (while (eq 1 (getvar "cmdactive"))
       (prompt "\nPick point: ")
       (command pause)
  )
  (setq head (entlast)
        hdata (entget head)
        newhdata nil
  )
  (if (= (dxf 70 hdata) 0)
     (setq hdata (subst (cons 70 1) (assoc 70 hdata) hdata))
  )
  (setq bulge (list (cons 42 0.5)))
  (if (= (dxf 0 hdata) "LWPOLYLINE")
    (progn
       (foreach itmcd hdata
         (if (= (car itmcd) 42)
            (setq itmcd (cons 42 0.5))
         )
         (setq newhdata (append newhdata (list itmcd)))
       )
       (entmod newhdata)
    )
    (progn
       (setq en (dxf -1 hdata))
       (while (setq en (entnext en))
         (setq ed (entget en))
         (setq ed (append ed bulge))
         (entmod ed)
       )
       (entmod hdata)
       (entupd head)
    )
  )
  (med_ret_ok)
  (princ)
)

(defun c:abl (/ pt pt1 pt2 pt3 pt4 dist lay)
    (setq pt (entsel "\nSelect bubble to add leader: ")
          lay (dxf 8 (entget (car pt)))
          pt1 (osnap (cadr pt) "center")
          pt2 (osnap (cadr pt) "quadrant")
          dist (abs (distance pt1 pt2))
          pt3 (getpoint pt1 "\nTo: ")
          pt3 (list (car pt3) (cadr pt3) (caddr pt1))
          pt4 (polar pt1 (angle pt1 pt3) dist)
    )
    (linemake pt3 pt4 lay)
    (princ)
)
(defun c:bracket( /); pt1 pt5 pt2 pt3 pt4 ang en)
  (med_cur_set "C:BRACKET")
  (progn
    (setvar "cmdecho" 0)
    (setvar "menuecho" 1)
    (setq curosmode (getvar "osmode"))
    (setq pt1(getpoint "\nFirst point of bracket: ")
          pt5(getpoint pt1 "Second point of bracket: ")
    )
    (setvar "snapang" (angle pt1 pt5))
    (setvar"orthomode"1)
    (setq ang (getangle (be pt1 pt5) "\nDirection of bracket: "))
    (setvar "snapang" 0.0)
    (setq pt2 (polar pt1 ang (* 0.10 (* _PLOTSCALE _SC)))
          pt3 (polar pt2 (angle pt1 pt5) (/ (distance pt1 pt5) 2))
          pt4 (polar pt3 ang (* 0.08 (* _PLOTSCALE _SC)))
    )
    (setvar "filletrad" (* (* _PLOTSCALE _SC) 0.05))
    (setvar "osmode" 0)
    (command "PLINE" PT1 "W" "0" "0" PT2 PT3 PT4 "")
    (setq en (entlast))
    (command "FILLET" "P" EN)
    (command "MIRROR" EN "" PT4 (be pt1 pt5) "N")
    (command "PEDIT" EN "J" EN (entlast) "" "")
    (setvar "osmode" curosmode)
    (med_ret_ok)
    (princ)
  )
)
(defun c:gr( / pt1 ept rot nep data)
   (setq pt1 (entsel "\nSelect Point near Endpoint of Line: ")
         ept (osnap (cadr pt1) "endp")
         rot (osnap (cadr pt1) "nea")
         nep (polar ept (angle ept rot)(* 1.000660721856467 (* 1.0 (getvar "dimscale") )
                                          (getvar "dimasz") 0.5))
         data (entget (car pt1))
   )
    (if (equal ept (cdr (assoc 10 data)))
        (setq data (subst (cons 10 nep) (assoc 10 data) data))
        (setq data (subst (cons 11 nep) (assoc 11 data) data))
    )
    (entmod data)
    (command "insert" "grabit" ept(* (* 1.0 (getvar "dimscale")) (getvar "dimasz") 0.5)
             "" rot)
)

(defun c:mbl(/ ans cenpt dist lay npt1 pt pt1 pt3 pt4 s1 s2 ss1)
   (med_cur_set "c:mbl")
   (setq pt (entsel "\nSelect leader to change of bubble to change: ")
         pt1 (dxf 11 (entget (car pt)))
         dist (abs (distance (osnap pt1 "center") pt1))
         pt3 (dxf 10 (entget (car pt)))
         pt1 (list (car pt1) (cadr pt1))
         cenpt (osnap pt1 "center")
         lay (getvar "clayer")
   )
   (command "layer" "s" (dxf 8 (entget (car pt))) "")
   (initget "Bubble Leader")
   (setq ans (getkword "\nChange Bubble point or Leader point <B>: "))
   (if (or (not ans) (= ans "Bubble"))
        (progn 
          (command "select" "C" pt1 pt1 "")
          (setq npt1 (getpoint pt3 "\nNew point of Bubble: ")
               
                ss1 (ssget "P")
                s1 (ssname ss1 0)
                s2 (ssname ss1 1)
          )
          (if (= (dxf 0 (entget s1)) "INSERT")
              (progn 
                 (command "erase" s2 "" "move" s1 "" (dxf 10 (entget s1)) npt1)
                 (setq pt4 (polar npt1 (angle npt1 pt3) dist))
                 (command "line" pt3 pt4 "")
              )
              (progn 
                  (command "erase" s1 "" "move" s2 "" (dxf 10 (entget s2)) npt1)
                  (setq pt4 (polar npt1 (angle npt1 pt3) dist))
                  (command "line" pt3 pt4 "")
              )
          )
        )
        (progn 
           (command "erase" pt "")
           (setq pt3 (getpoint cenpt  "\nNew leader point: ")
                 pt4 (polar cenpt (angle cenpt pt3) dist)
           )
           (command "line" pt3 pt4 "")
        )
   )
   (command "layer" "s" lay "")
   (med_ret_ok)
   (princ)

)
(defun C:HDTAG ()
	(setq ctlt (getvar "CELTYPE")
		  ctlay (getvar "CLAYER")
	      cattdia (getvar "attdia")
	)
	(ltback nil)
	(smlayer _ECTAG)
	(setq ConduitEntity (entsel "\nSelect Conduit to Tag: "))
	(if ConduitEntity
		(progn
			(setq ConduitPoint (osnap (cadr ConduitEntity) "NEA")
				  ConduitEntity (car ConduitEntity)
				  ConduitData (xdataget ConduitEntity _CONDUIT)
			)
			(if ConduitData
				(setq ConduitSize (rtos (nth 2 ConduitData) 4 2)
					  ConduitTag (nth 1 ConduitData)
				)
				(setq ConduitSize (getstring "\nConduit Size: ")
					  ConduitTag (getstring T "\nConduit Tag: ")
				)
			)
		)
		(setq ConduitSize (getstring "\nConduit Size: ")
			  ConduitTag (getstring T "\nConduit Tag: ")
		)
	)
	(cond
		((< (strlen ConduitTag) 9)
			(setq hdtagblockname "hd1"
				  hddist 1.0
			)
		)
		((< (strlen ConduitTag) 13)
			(setq hdtagblockname "hd2"
				  hddist 1.375
			)
		)
		((< (strlen ConduitTag) 17)
			(setq hdtagblockname "hd3"
				  hddist 1.7375
			)
		)
		((< (strlen ConduitTag) 21)
			(setq hdtagblockname "hd4"
				  hddist 2.1375
			)
		)
		((< (strlen ConduitTag) 25)
			(setq hdtagblockname "hd5"
				  hddist 2.575
			)
		)
		(T
			(setq hdtagblockname "hd6"
				  hddist 2.9375
			)
		)
	)
	(setq mvdist (* _SC hddist)
		  keyent (medleader "grabit" nil 0.5 _ECTAG)
		  keydata (bld_lw_ptlist keyent)
		  keydata (car keydata)
		  keydata (reverse keydata)
		  keypt1 (cdr (nth 1 keydata))
		  keypt2 (cdr (nth 0 keydata))
		  keyrot(angle keypt1 keypt2)
		  mvdata nil
	)
	(cond
	   ((or (< keyrot (* PI 0.25)) (>= keyrot (* PI 1.75)))
		  (setq keyrot 0.0
				mvdata nil
		  )
	   )
	   ((and (>= keyrot (* PI 0.25)) (< keyrot (* PI 0.75)))
		  (setq keyrot (* PI 0.5)
				mvdata nil
		  )
	   )
	   ((and (>= keyrot (* PI 0.75)) (< keyrot (* PI 1.25)))
		  (setq keyrot 0.0
				keypt2 (polar keypt2 PI (- mvdist (* _PLOTSCALE _SC 0.125)))
				mvdata PI
		  )
	   )
	   ((and (>= keyrot (* PI 1.25)) (< keyrot (* PI 1.75)))
		  (setq keyrot (* PI 0.5)
				keypt2 (polar keypt2 (* PI 1.5) (- mvdist (* _PLOTSCALE _SC 0.125)))
				mvdata (* PI 1.5)
		  )
	   )
	)
	(setvar "ATTDIA" 0)
	(setvar "ATTREQ" 1)
	(command "insert" hdtagblockname keypt2 (* _PLOTSCALE _SC) (* _PLOTSCALE _SC) (angtos keyrot)
		ConduitTag ConduitSize
	)
	(setvar "ATTDIA" cattdia)
	(setq hdent (entlast)
		  atent (sel_att_ent hdent "CONSIZE" nil)
		  atdata (entget atent)
		  txtbx (textbox atdata)
		  addon (car (cadr txtbx))
		  mvdist (+ mvdist addon)
	)
	(if mvdata
		(progn
			(move_attrib hdent mvdata mvdist "CONSIZE")
		)
	)
	(setvar "CLAYER" ctlay)
	(ltback ctlt)
)
		
(defun c:hdtagold( / info blk)
  (med_cur_set "C:HDTAG")
  (smlayer _MEDTEXT)
  (setq curatdia (getvar "ATTDIA"))
  (setq info (getstring T "\nTag Information: "))
  (if (< (strlen info) 9)
	    (setq blk "hd1")
	    (progn
	      (if (< (strlen info) 13)
	        (setq blk "hd2")
                (setq blk "hd3")
	      )
	    )
  ) 
  (prompt "\nInsertion Pont: ")
  (setvar "ATTDIA" 0)
  (command "insert" blk "pscale" (* _PLOTSCALE _SC) pause )
  (prompt "\nRotation: ")
  (command (* _PLOTSCALE _SC) "" pause info)
  (setvar "ATTDIA" curatdia)
  (med_ret_ok)
  (princ)
)


(defun c:mb( / bsize id qty pt1 pt2 pt3 ang)
    (smlayer _EMATBUB)
    (setvar "attdia" 0)
    (setvar "cmdecho" 0)
    (setq bsize (* (* _PLOTSCALE _SC) 0.1875)
          etp "E" ;(getstring "Material code: ")
          id (getstring "Material I.D.#: ")
          qty (getstring "Quantity <1>: ")
    )
    (if (not qty)
          (setq qty 1)
    )
    (setq pt1 (getpoint "\nPickpoint: ")
          pt2 (getpoint pt1 "Pick point of first bubble: ")
    )
    (prompt "\nPick point of first bubble: ")
    (while (< (strlen id) 3)
	      (setq id (strcat "0" id))
    )
    (command "insert" "matbub" pt2 (* 1.0 _SC) "" "" id qty etp "")
    (setq pt3 (polar pt2 (angle pt2 pt1) bsize)
    )
    (command  "line" pt1 pt3 "")
    (setq id nil)
    (if (/= "" (setq id (getstring "\nMaterial I.D.#: ")))
        (progn
            (setq ang (getangle pt2 "\nDirection of bubbles: ")
                  pt2 (polar pt2 ang (* 2 bsize))
            )
	    (while (< (strlen id) 3)
	      (setq id (strcat "0" id))
	     )
            (command "insert" "" pt2 (* 1.0 _SC) "" "" id qty etp "")
            (while (/= "" (setq id (getstring "\nMaterial I.D.#: ")))
              (setq pt2 (polar pt2 ang (* 2 bsize)))
              (while (< (strlen id) 3)
	         (setq id (strcat "0" id))
	      )
	      (command "insert" "" pt2 (* 1.0 _SC) "" "" id qty etp "")
            )
        )
    )
)

(defun c:mb1( / bsize id qty pt1 pt2 pt3 ang)
    (smlayer _EMATBUB)
    (setvar "attdia" 0)
    (setvar "cmdecho" 0)
    (setq bsize (* (* 1.0 _SC) 0.1875)
	  id (getstring "Material I.D.#: ")
    )
    (setq pt1 (getpoint "\nPickpoint: ")
          pt2 (getpoint pt1 "Pick point of first bubble: ")
    )
    (prompt "\nPick point of first bubble: ")
    (while (< (strlen id) 3)
	      (setq id (strcat "0" id))
    )
    (command "insert" "mat_bub" pt2 (* 1.0 _SC) "" "" id)
    (setq pt3 (polar pt2 (angle pt2 pt1) bsize)
    )
    (command  "dim1" "lea" pt1 pt3 nil)
    (setq id nil)
    (if (/= "" (setq id (getstring "\nMaterial I.D.#: ")))
        (progn
            (setq ang (getangle pt2 "\nDirection of bubbles: ")
                  pt2 (polar pt2 ang (* 2 bsize))
            )
	    (while (< (strlen id) 3)
	      (setq id (strcat "0" id))
	     )
            (command "insert" "" pt2 (* 1.0 _SC) "" "" id)
            (while (/= "" (setq id (getstring "\nMaterial I.D.#: ")))
              (setq pt2 (polar pt2 ang (* 2 bsize)))
              (while (< (strlen id) 3)
	         (setq id (strcat "0" id))
	      )
	      (command "insert" "" pt2 (* 1.0 _SC) "" "" id)
            )
        )
    )
)

(defun c:boxcloud()
   (medsmlayer _REVISION)
   (if (not xseglen)
       (setq xseglen (* 0.25 (* _PLOTSCALE (getvar "dimscale")))
             xlen xseglen
       )
       (setq xlen xseglen)
   )
   (if (not yseglen)
       (setq yseglen (* 0.25 (* _PLOTSCALE (getvar "dimscale")))
             ylen yseglen
       )
       (setq ylen yseglen)
   )
      
   (setq pt1 (getpoint "\nFirst Corner of Cloud: ")
         pt3 (getcorner pt1 "\nSecond Corner of Cloud: ")
         pt2 (list (car pt3) (cadr pt1))
         pt4 (list (car pt1) (cadr pt3))
         d1  (distance pt1 pt2)
         d2  (distance pt2 pt3)
    )
    (setq xseglen (getdist pt1 (strcat "\nX Distance for Clouding <"
                                        (rtos xseglen) ">: "))
    )
    (if (not xseglen)
      (setq xseglen xlen)
    )
    (setq yseglen (getdist pt1 (strcat "\nY Distance for Clouding <"
                                        (rtos yseglen) ">: "))
    )
    (if (not yseglen)
      (setq yseglen ylen)
    )
    (setq npt (polar pt1 (angle pt1 pt2) xseglen))
    (command "pline" pt1 npt)
    (while (> d1 (abs (distance pt1 npt)))
       (setq npt (polar npt (angle pt1 pt2) xseglen))
       (command npt)
    )
    (while (> d2 (abs (distance pt2 npt)))
       (setq npt (polar npt (angle pt2 pt3) xseglen))
       (command npt)
    )
    (while (> d1 (abs (distance pt3 npt)))
       (setq npt (polar npt (angle pt3 pt4) xseglen))
       (command npt)   
    )
    (while (> (- d2 yseglen) (abs (distance pt4 npt)))
       (setq npt (polar npt (angle pt4 pt1) xseglen))
       (command npt)
    )
   (command "c")
   (setq head (entlast)
        hdata (entget head)
        newhdata nil
   )
   (if (= (dxf 70 hdata) 0)
      (setq hdata (subst (cons 70 1) (assoc 70 hdata) hdata))
   )
   (setq bulge (list (cons 42 0.5)))
   (if (= (dxf 0 hdata) "LWPOLYLINE")
     (progn
        (foreach itmcd hdata
          (if (= (car itmcd) 42)
             (setq itmcd (cons 42 0.5))
         )
          (setq newhdata (append newhdata (list itmcd)))
       )
        (entmod newhdata)
     )
     (progn
        (setq en (dxf -1 hdata))
        (while (setq en (entnext en))
          (setq ed (entget en))
          (setq ed (append ed bulge))
           (entmod ed)
        )
        (entmod hdata)
        (entupd head)
     )
   )
   (princ)
)

(princ "Done.")
