(defun MEDSetTextStyleHeight(StyleName NewHeight)
	(setq AcadObject (vlax-get-acad-object)
		  AcadDocument (vla-get-activedocument AcadObject)
		  DocTextStyles (vla-get-TextStyles AcadDocument)
		  StyleObject (vl-catch-all-apply 'vla-Item (list DocTextStyles StyleName))
	)
	(if (vl-catch-all-error-p StyleObject) 
			(princ "\nStyle Not Found")
			(vla-put-height StyleObject NewHeight)
	)
)
(defun MEDMakeTextStyle (StyleDataList)
	(setq TextStyleName (nth 1 StyleDataList)
		  TextStyleFont (nth 2 StyleDataList)
		  TextStyleHeight (nth 3 StyleDataList)
		  TextStyleWidth (nth 4 StyleDataList)
		  AcadObject (vlax-get-acad-object)
		  AcadDocument (vla-get-activedocument AcadObject)
		  DocTextStyles (vla-get-TextStyles AcadDocument)
		  StyleObject (vl-catch-all-apply 'vla-Add (list DocTextStyles TextStyleName))
	)
	(if (vl-catch-all-error-p StyleObject) 
		(princ "\nUnable To Create Text Style")
		(progn
			(vla-put-height StyleObject TextStyleHeight)
			(vla-put-width StyleObject TextStyleWidth)
			(vla-put-fontfile StyleObject TextStyleFont)
		)
	)
)
