(princ "\nLoading MEDTray...")
(defun c:trayrel()
  (traylrre PI (+ _TRFITSTRT 1))
  (princ)
)
(defun c:trayrer()
  (traylrre 0.0 (+ _TRFITSTRT 2))
  (princ)
)
(defun c:tray60()
  (trayang (/ PI 3.0) (+ _TRFITSTRT 7) nil)
  (princ)
)
(defun c:tray45()
  (trayang (* PI 0.25) (+ _TRFITSTRT 10) nil)
  (princ)
)
(defun c:tray30()
  (trayang (/ PI 6.0) (+ _TRFITSTRT 13) nil)
  (princ)
)
(defun c:traysize(/ tsz_sizelist)
   (setq tsz_sizelist (list (list 6.0 "a")
                            (list 9.0 "b")
                            (list 12.0 "c")
                            (list 18.0 "d")
                            (list 24.0 "e")
                            (list 30.0 "f")
                            (list 36.0 "g")
                            (list 42.0 "h")
                            (list 48.0 "i")
                      )
         tsz_depthlist(list (list 3.0 "a")
                            (list 4.0 "b")
                            (list 6.0 "c")
                      )
         tsz_radiuslist(list (list 12.0 "a")
                             (list 24.0 "b")
                             (list 36.0 "c")
                             (list 48.0 "d")
                       )
   )
   (setq curwidth (assoc _TRSIZE tsz_sizelist)
         curwidth (strcat "size" (nth 1 curwidth))
         curdepth (assoc _TRDEPTH tsz_depthlist)
         curdepth (strcat "depth" (nth 1 curdepth))
         curradius(assoc _TRRAD tsz_radiuslist)
         curradius(strcat "radius" (nth 1 curradius))
         tsz_width _TRSIZE
         tsz_depth _TRDEPTH
         tsz_radius _TRRAD
         tsz_add    _TRFITTADD
   )
   (if (> (setq index_val (load_dialog "MED")) 0)
      (progn
         (if (new_dialog "Med_TraySize" index_val)
            (progn 
                (set_tile curwidth "1")
                (set_tile curdepth "1")
                (set_tile curradius "1")
                (action_tile "sizea" "(setq tsz_width 6.0)")
                (action_tile "sizeb" "(setq tsz_width 9.0)")
                (action_tile "sizec" "(setq tsz_width 12.0)")
                (action_tile "sized" "(setq tsz_width 18.0)")
                (action_tile "sizee" "(setq tsz_width 24.0)")
                (action_tile "sizef" "(setq tsz_width 30.0)")
                (action_tile "sizeg" "(setq tsz_width 36.0)")
                (action_tile "sizeh" "(setq tsz_width 42.0)")
                (action_tile "sizei" "(setq tsz_width 48.0)")
                (action_tile "deptha" "(setq tsz_depth 3.0)")
                (action_tile "depthb" "(setq tsz_depth 4.0)")
                (action_tile "depthc" "(setq tsz_depth 6.0)")
                (action_tile "radiusa" "(setq tsz_radius 12.0 tsz_add 0)")
                (action_tile "radiusb" "(setq tsz_radius 24.0 tsz_add 1)")
                (action_tile "radiusc" "(setq tsz_radius 36.0 tsz_add 2)")
                (action_tile "radiusd" "(setq tsz_radius 48.0 tsz_add 120)")
                (action_tile "accept" "(done_dialog 1)")
                (action_tile "cancel" "(done_dialog 0)")
                (setq result (start_dialog))
            )
         )
         (unload_dialog index_val)
         (if (= result 1)
          (progn
           (setq _TRSIZE tsz_width
                 _TRDEPTH tsz_depth
                 _TRRAD tsz_radius
                 _TRFITTADD tsz_add
           )
           (c:tray)
          )
         )
      )
   )
)


(defun c:vtray( / cltp clay trpt1 trpt2 trtag xdlist)
   (setq oldvert_tray _VERTICALTRAY
         _VERTICALTRAY T
   )
   (c:tray)
   (setq _VERTICALTRAY oldvert_tray
         oldvert_tray nil
   )
   (terpri)
)
(defun c:channel( / tmp_trcode tmp_trtype tmp_trdepth tmp_trsize)
  (setq tmp_trcode  _TRCODE
        tmp_trtype  _TRTYPE
        tmp_trdepth _TRDEPTH
        tmp_trsize  _TRSIZE
        tmp_flange  _TRAYFLANGE
        _TRCODE     _CHANCODE
        _TRTYPE     0
        _TRDEPTH    _CHANDEPTH
        _TRSIZE     _CHANSIZE
        _TRAYFLANGE 0.0
  )
  (c:tray)
  (setq _TRCODE  tmp_trcode  
        _TRTYPE  tmp_trtype  
        _TRDEPTH tmp_trdepth 
        _TRSIZE  tmp_trsize
        _TRAYFLANGE tmp_flange
  )

  (princ)
)
(defun opposite_tray_endpt (pln_hdent pl_endpt / pl_data ptlist ret_pt ptlistlen)
  (if (= (dxf 0 (entget pln_hdent)) "LWPOLYLINE")
    (progn
      (setq ptlist (bld_lw_ptlist pln_hdent)
	    ptlist (nth 0 ptlist)
	    otept1 (nth 0 ptlist)
	    otept2 (nth 1 ptlist)
      )
      (if (> (length pl_endpt) 2)
	(setq pl_endpt (list (nth 0 pl_endpt) (nth 1 pl_endpt)))
      )
      (if (equal (cdr otept1) pl_endpt 0.0000000001)
	(setq ret_pt (cdr otept2))
	(setq ret_pt (cdr otept1))
      )
    )
    (progn
      (setq pl_data (entget (entnext pln_hdent))
            ptlist  nil
      )
      (while (/= "SEQEND" (dxf 0 pl_data))
        (setq ptlist (append ptlist (list (dxf 10 pl_data)))
              pl_data (entget (entnext (dxf -1 pl_data)))
        )
      )
     (setq ptlistlen (length ptlist))
     (if (equal (nth 0 ptlist) pl_endpt)
       (progn
         (setq ret_pt (nth (1- ptlistlen) ptlist))
       )
       (progn
         (setq ret_pt (nth 0 ptlist))
       )
     )
    )
  )
  ret_pt
)

(defun c:vtray60()
  (setq olverttr _VERTICALTRAY
        _VERTICALTRAY T
  )
  (initget "Inside Outside")
  (setq fittype (getkword "\nInside or <Outside>: "))
  (if (or (not fittype) (= "Outside" fittype))
    (setq trfitcd (+ _TRFITVSTR 9))
    (setq trfitcd (+ _TRFITVSTR 6))
  )
  (trayang (/ PI 3.0) trfitcd nil)
  (setq _VERTICALTRAY olverttr
        olverttr nil
  )
  (princ)
)
(defun c:vtray45()
  (setq olverttr _VERTICALTRAY
        _VERTICALTRAY T
  )
  (initget "Inside Outside")
  (setq fittype (getkword "\nInside or <Outside>: "))
  (if (or (not fittype) (= "Outside" fittype))
    (setq trfitcd (+ _TRFITVSTR 15))
    (setq trfitcd (+ _TRFITVSTR 12))
  )
  (trayang (* PI 0.25) trfitcd nil)
  (setq _VERTICALTRAY olverttr
        olverttr nil
  )
  (princ)
)
(defun c:vtray30()
  (setq olverttr _VERTICALTRAY
        _VERTICALTRAY T
  )
  (initget "Inside Outside")
  (setq fittype (getkword "\nInside or <Outside>: "))
  (if (or (not fittype) (= "Outside" fittype))
    (setq trfitcd (+ _TRFITVSTR 21))
    (setq trfitcd (+ _TRFITVSTR 18))
  )
  (trayang (/ PI 6.0) trfitcd nil)
  (setq _VERTICALTRAY olverttr
        olverttr nil
  )
  (princ)
)
(defun c:chantee()
  (setq _CHANTEE T)
  (c:traytee)
)
(defun c:chancross()
  (setq _CHANTEE T)
  (c:traycross)
)
(defun c:chanv90()
  (setq _CHANTEE T)
  (c:trayv90)
)


(defun c:chan60()
  (setq _CHANTEE T)
  (trayang (/ PI 3.0) (+ _CHANFITST 3) nil)
  (setq _CHANTEE nil)
  (princ)
)
(defun c:chan45()
  (setq _CHANTEE T)
  (trayang (* PI 0.25) (+ _CHANFITST 6) nil)
  (setq _CHANTEE nil)
  (princ)
)
(defun c:chan30()
  (setq _CHANTEE T)
  (trayang (/ PI 6.0) (+ _CHANFITST 9) nil)
  (setq _CHANTEE nil)
  (princ)
)
(defun c:chan90()
  (setq _CHANTEE T)
  (MEDMtray90 nil _CHANFITST)
  (setq _CHANTEE nil)
  (princ)
)
(defun c:chanoff()
   (setq _CHANTEE T)
   (c:trayoff)
   (setq _CHANTEE nil)
)
;;
;;Tray functions 
;;
(defun xdrtray (xdrelent1 xdmainent / handmdata handr1data
;                xdrelent1 rent1data 
;                 rxdadd mentdata mxdadd
                )
   (setq handr1data (dxf 5 (entget xdrelent1)))
   (setq mentdata (entget xdmainent (list "MED_*"))
         mxdadd   (list '(1002 . "}"))
   )
   (if _VERTICALTRAY
      (setq mxdadd(cons (cons 1000 "VERTICAL") mxdadd))
   )
   (setq mxdadd   (cons (cons 1000 handr1data) mxdadd)
         mxdadd   (cons '(1002 . "{") mxdadd)
         mxdadd   (cons _DOUBLE  mxdadd)
         mxdadd   (cons -3 (cons mxdadd (cdr (assoc -3 mentdata))))
         mentdata (subst mxdadd (assoc -3 mentdata) mentdata)
   )
   (if _RESETVTRAY
      (setq _VERTICALTRAY nil
            _RESETVTRAY   nil
      )
   )
   (entmod mentdata) 
)

(defun maketray (traylist closeflag layerset / clay vtxt sqend vtxt vert vertxt)
  (setq plin '((0 . "LWPOLYLINE") (100 . "AcDbEntity") (67 . 0)))
  (setq clay (getvar "CLAYER"))
  (if (not layerset)
     (setq bldlayer (nth 0 _MEDTRAY)
           layerset _MEDTRAY
     )
     (setq bldlayer (nth 0 layerset))
  )
  (if (not (tblsearch "layer" bldlayer))
    (progn
       (smlayer layerset)
       (setvar "CLAYER" clay)
    )
  )
  (setq plin (append plin (list (cons 8 bldlayer))))
  (setq plin (append plin (list (cons 100 "AcDbPolyline") (cons 67 0))))
  (setq ptlistlen (length traylist)
        plin (append plin (list (cons 90 ptlistlen)))
  )
  (if closeflag
     (setq plin  (append plin (list (cons 70 1))))
  )
  (setq plin (append plin (list (cons 43 0.0) (cons 38 (getvar "ELEVATION")) (cons 39 0.0))))

  (foreach vertxt traylist
     (setq vert (cons 10 (nth 0 vertxt))
           ver1 (cons 40 0.0)
           ver2 (cons 41 0.0)
     )
     (if (nth 1 vertxt)
         (setq ver3 (cons 42 (nth 1 vertxt)))
         (setq ver3 (cons 42 0.0))
     )
     (setq plin (append plin (list vert ver1 ver2 ver3)))
  )
  (if _ZFLAG
    (setq twoten (cons 210 (list 0.0 -1.0 0.0))
          plin (append plin (list twoten))
    )
  )
  (entmake plin)
)   


(defun tray_brk_rot (br_pt br_bldata)

  (setq br_data   (if (setq br_ns (nentselp "\n" br_pt)) (entget (car br_ns))) ; traytee-s1 nil guard
        br_d1     (nth 0 br_bldata)
        br_d2     (nth 1 br_bldata)
        br_d3     (nth 2 br_bldata)
        br_d4     (nth 3 br_bldata)
        rt_spec   (nth 4 br_bldata)
        br_list   (list br_d1 br_d2 br_d3 br_d4)
        bl_sz     (* 4.5 (if (numberp _PLOTSCALE) _PLOTSCALE 1.0)) ; traytee-s1 scale-aware probe
        pckbx     (getvar "PICKBOX")
  )
  (setvar "PICKBOX" 0)
  (if (= _USERROT 1)
     (setq rt_spec 4)
  )
  (cond 
       ((not rt_spec)
          (setq br_ang 0.0)
          (med_brk_rot br_ang br_pt br_list)

       )
       ((= rt_spec 0)
          (setq br_pt2 (osnap br_pt "MID"))
          (if (or (equal (dxf 10 br_data) br_pt)
                  (equal (osnap (polar br_pt2 (angle (dxf 10 br_data) br_pt2)
                                              0.125)
                                              "END") br_pt)
              )
              (progn 
                (setq br_ang (angle br_pt br_pt2))
              )
              (progn
                (if (not _TANG)
                   (progn
                      (setq br_pt2 (osnap (cadr (entsel "\nSelect point on line for rotation: ")) "NEA"))
                      (if (not br_pt2)
                        (setq br_pt2 (osnap br_pt "MID"))
                      )
                      (setq br_ang (angle br_pt br_pt2))
                   )
                )
              )
          )
          (if _TANG
            (med_brk_out _TANG br_pt br_list T)
            (med_brk_out br_ang br_pt br_list T)
          )
       )
       ((= rt_spec 1)
          (setq br_pt2 (osnap br_pt "MID")
                br_ang (angle br_pt br_pt2)
          )
          (med_brk_out br_ang br_pt br_list T)
       )
       ((= rt_spec 22)
          (setq br_pt2 (osnap br_pt "MID")
                tmp_ang(angle br_pt br_pt2)
                br_pt3 (polar br_pt (+ (* 0.5 PI) tmp_ang) bl_sz)
                br_pt4 (polar br_pt (+ (* 1.5 PI) tmp_ang) bl_sz)
          )
          (if (nentselp "\n" br_pt3)
              (setq br_ang tmp_ang)
              (setq br_ang (angle br_pt br_pt4))
          )
          (med_brk_out br_ang br_pt br_list T)
       )   
       ((= rt_spec 24)
          (setq br_pt2 (osnap br_pt "MID")
                tmp_ang(angle br_pt br_pt2)
                br_pt3 (polar br_pt (+ (* 0.5 PI) tmp_ang) bl_sz)
                br_pt4 (polar br_pt (+ (* 1.5 PI) tmp_ang) bl_sz)
          )
          (if (nentselp "\n" br_pt4)
            (progn
              (setq br_ang tmp_ang)
              (prompt "\nPT4")
            )
            (progn
              (setq br_ang (angle br_pt br_pt3))
              (prompt "\nPT3")
            )
          )
          (med_brk_out br_ang br_pt br_list T)
       )   
       ((= rt_spec 3)
          (setq br_pt2 (osnap br_pt "MID")
                tmp_ang(angle br_pt br_pt2)
                br_pt3 (polar br_pt (+ (* 0.5 PI) tmp_ang) bl_sz)
                br_pt4 (polar br_pt (+ (* 1.5 PI) tmp_ang) bl_sz)
          )
          (if (and (nentselp "\n" br_pt3) (nentselp "\n" br_pt4))
              (setq br_ang tmp_ang)
              (progn
                (if (nentselp "\n" br_pt3)
                    (setq br_ang (angle br_pt br_pt3))
                    (setq br_ang (angle br_pt br_pt4))
                )
              )
          )
          (med_brk_out br_ang br_pt br_list T)
       )   
       ((= rt_spec 4)
          (setq br_pt2 (osnap br_pt "MID")
                tmp_ang (angle br_pt br_pt2)
                br_ang (getangle br_pt "\nRotation: ")
                sub_ang (- tmp_ang br_ang)
          )
          (if (> sub_ang 0.0)
             (setq br_ang tmp_ang)
             (setq br_ang br_ang)
          )
          (med_brk_out br_ang br_pt br_list T)

       )

  )
  (setvar "PICKBOX" pckbx)
  br_ang
)

; this function will return one of two items pending on a value of ckpt
; if ckpt is true then dblchk will erase entities assosiated with
; a double line conduit found at the point specified by ckpt

(defun traychck ( ckpt); / dblnum dblcnt dblent dbldata dblinfo condata dblsz dbllett)
  ;; traytee-s1 2026-10-28: nil-safe (nothing under point -> no-op). Erases here are
  ;; inside the caller's UNDO group, so Escape/fail rolls the outlines back.
  (setq trayss  (ssget "C" ckpt ckpt)
        trsslen (if trayss (sslength trayss) 0)
        trcnt   0
        TR_MAIN (ssadd)
  )
  (while (< trcnt trsslen)
      (setq dblent  (ssname trayss trcnt)
            dbldata (xdataget dblent _DOUBLE)
            trcnt (1+ trcnt)
      )
      (if dbldata
        (progn
          (setq dbl1ent (handent (nth 1 dbldata))
                TR_MAIN (ssadd dblent TR_MAIN)
          )
          (if dbl1ent
            (progn
              (if (entget dbl1ent)
                (entdel dbl1ent)
              )
            )
          )
        )
      )
  )
)

(defun get_tray_data(tray_ss / cnt num cmsize tray_size cmpent cmlent rtsize
                              tray_code)
;;;
;;;     Variable Name  ||    Description
;;;     ---------------------------------------------------------------
;;;     tray_ss        ||    Selection set of entities at insertion point
;;;     cnt            ||    counter variable
;;;     num            ||    selection set length
;;;     cmsize         ||    size stored in base entity
;;;     tray_size      ||    size of tray_duit set to equal cmsize
;;;     cmpent         ||    compare entity name for filtering therough sset
;;;     cmlent         ||    entity name to be used as base entity
;;;     rtsize         ||    list of data to be returned to calling function
;;;     tray_code      ||    tray_duit code used in xdata

   (setq num (sslength tray_ss)
         cnt 0
         cmsize 0
         cssize 100
   )
   (while (< cnt num)
     (setq cmpent (ssname tray_ss cnt)
           tray_size(xdataget cmpent _TRAY)
     )
     (if (not tray_size)
        (progn
          (setq tray_size (xdataget cmpent _FITTING))
        )
     )
     (if tray_size
       (progn
         (setq tr_tag   (nth 1 tray_size)
	             tr_code  (nth 3 tray_size)
	             tr_size  (nth 2 tray_size)
	             tr_dpth  (nth 5 tray_size)
	             tr_flng  (nth 7 tray_size)

               
         )
         (if (> tr_size cmsize)
           (setq cmsize tr_size
                 cmlent cmpent
                 mxtag  tr_tag
                 mxcode tr_code
                 mxdpth tr_dpth
                 mxent  cmpent
           )
         )
         (if (< tr_size cssize)
           (setq cssize tr_size
                 cslent cmpent
                 mntag  tr_tag
                 mncode tr_code
                 mdpth  tr_dpth
                 mnent  cmpent
           )
         )

       )
     )
     (setq cnt (1+ cnt))
   )
   (if (/= cmsize 0)
       (setq rt_size (list cmsize mxtag mxcode mxdpth cssize mntag mncode mndpth mxent mnent tr_flng))
   )
   rt_size
)


(defun vtrayfitsel ( outopt inopt / degfit1)
   (setq olverttr _VERTICALTRAY
         _VERTICALTRAY T
   )
   (initget "Inside Outside")
   (setq fittype (getkword "\nInside or <Outside>: "))
   (if (or (not fittype) (= "Outside" fittype))
     (setq degfit1 (+ _TRFITVSTR outopt))
     (setq degfit1 (+ _TRFITVSTR inopt))
   )
   degfit1
)


(defun tryupdn( traydir trltype trptlist startingelev)
   (setq cltp (getvar "celtype"))
   (ltback trltype)
   (setq clay (getvar "CLAYER")
         acttraydir nil
   )
   (if (not trptlist)
     (progn
       (while (not (setq trbasent (entsel "\nSelect Tray item"))))
       (setq pt1 (osnap (cadr trbasent) "ENDPoint")
	     opt1(opposite_tray_endpt (car trbasent) pt1)
	     pt3 pt1
	     
       )
     )
     (progn
      (setq pt1 (nth 0 trptlist)
            pt3 (nth 1 trptlist)
      )
     )
   )
   (setq pt2  (list (car pt3) (cadr pt1) (caddr pt1))
         pt4  (list (car pt1) (cadr pt3) (caddr pt1))
	 trsizess (ssget "c" pt1 pt3)
	 trsize (get_tray_data trsizess)
         trdnverdata nil
         trdncnt 0
         trsizesslen (sslength trsizess)
   )
   (if (not startingelev)
     (progn
       (while (and (not trdnverdata) (< trdncnt trsizesslen))
         (setq trdnverdata (xdataget (ssname trsizess trdncnt) _FITTING)
	       trdncnt (1+ trdncnt)
         )
       )
       (if trdnverdata
	 (progn
           (setq trdnverdata (vtrayxdataget (ssname trsizess (1- trdncnt)))
		 trdnentdata (entget (ssname trsizess (1- trdncnt)))
		 trdnentelev (dxf 38 trdnentdata)
           )
           (if (= (nth 3 trdnverdata) 1)
	     (progn
	       (setq traydir "Up"
		     acttraydir "Up"
	   	     startingelev (+ trdnentelev (nth 3 trsize) (nth 1 trdnverdata) (nth 2 trdnverdata))
               )
	     )
	     (progn
	       (setq traydir "Down"
		     acttraydir "Down"
	   	     startingelev (- trdnentelev (+ (nth 1 trdnverdata) (nth 2 trdnverdata)))
               )
	     )
	   )
	 )
       )
     )
	   
   )
   (if _CHANTEE
     (setq trcode _CHANCODE)
     (setq trcode (+ _TRCODE _TRTYPE))
   )
   (setq trsz   (nth 0 trsize)
         trdpth (nth 3 trsize)
         trtag  (nth 1 trsize)
	 trlay  (nth 0 _MEDTRAY)
   )
   (if (not trptlist)
     (setq ang (angle pt1 opt1)
	   pt1 (polar pt1 (+ ang (* PI 0.5)) (* _PLOTSCALE (* 0.5 trsz)))
	   pt2 (polar pt1 (+ PI ang) (* _PLOTSCALE trdpth))
	   pt3 (polar pt2 (- ang (* PI 0.5)) (* _PLOTSCALE trsz))
	   pt4 (polar pt3 ang (* _PLOTSCALE trdpth))
     )
     (setq angofln(atan (/ trdpth trsz))
	 angpts (angle pt1 pt3)
	 pt2    (polar pt3 (+ PI (+ angpts angofln)) (* _PLOTSCALE trsz))
	 pt4    (polar pt1 (+ angpts angofln) (* _PLOTSCALE trsz))
     )
   )
  
   (if (not traydir)
     (setq traydir "Down")
   )
   (if (not trptlist)
      (setq mdprmpt(strcat "\nLength of " (clookup trcode trsz _TRAY)
                        " traveling " traydir
                        " <" (rtos _MEDDIST) ">: "
                   )
            trdist (getdist (be pt1 pt3) mdprmpt)
      )
      (setq trdist (nth 2 trptlist))
   )
   (if (not trdist)
      (setq trdist _MEDDIST)
      (setq _MEDDIST trdist)
   )
   (smlayer (list trlay nil nil))
   (if startingelev
     (progn
       (setq tryupdncurelev (getvar "ELEVATION"))
       (setvar "ELEVATION" startingelev)
     )
   )
   (pmake (list pt1 pt3 pt4 pt2) T)
   (if (= (type traydir) (type (list "")))
     (setq acttraydir (nth 1 traydir)
	   traydir (nth 0 traydir)
     )
   )
   (if (= traydir "Down")
     (progn
       (chg_ent_ltype (entlast) TR_DNLTYPE)
     )
     
   )
   (chg_tray_pl_wdth (entlast) _TR_X_WIDTH)
   (setq mlist (list (list (be pt1 pt4) nil)
                     (list (be pt2 pt3) nil)
               )
   )
   (maketray mlist nil _MEDCENLAY)
        
   (setq xdlist (bld_tray trcode trsz trtag trdist trdpth "F"))
   (xdatadd (entlast) xdlist)
   (if (= acttraydir "Down")
       (setq vtrydir -1)
       (setq vtrydir 1)
   )
   (addvtraydata (entlast) (list 0.0 0.0 vtrydir 0.0))
   (if startingelev
     (progn
       (setvar "ELEVATION" tryupdncurelev)
     )
   )
   (smlayer (list clay nil nil))
   (ltback cltp)
   (princ)
)

(defun c:vtrayoff()
  (med_cur_set "c:vtrayoff")
  (setq _VERTICALTRAY T)
  (C:TRAYOFF)
  (setq _VERTICALTRAY nil)
  (med_ret_ok)
  (princ)
)

(defun pmake ( ptlist plclose ) ;zflag / );plin vtxt sqend)
  (setq plin '((0 . "LWPOLYLINE") (100 . "AcDbEntity") (67 . 0)))
  (if CR_LAYER
   (progn
     (setq plin (append plin (list (cons 8 CR_LAYER)))
     )
   )
  )
  (setq plin (append plin (list (cons 100 "AcDbPolyline") (cons 67 0))))
  (setq ptlistlen (length ptlist)

        plin (append plin (list (cons 90 ptlistlen)))
  )
  (if plclose
     (setq plin  (append plin (list (cons 70 1))))
  )
  (if _USEELEV
     (setq elev _USEELEV
           _USEELEV nil
     )
     (setq elev (getvar "ELEVATION"))
  )
  (setq plin (append plin (list (cons 43 0.0) (cons 38 elev) (cons 39 0.0))))

  (foreach pt ptlist
     (setq vert (cons 10 pt)
           ver1 (cons 40 0.0)
           ver2 (cons 41 0.0)
           ver3 (cons 42 0.0)
           plin (append plin (list vert ver1 ver2 ver3))
     )
  )
  (if _ZFLAG
    (setq twoten (cons 210 (list 0.0 -1.0 0.0))
          plin (append plin (list twoten))
          _ZFLAG nil
    )
  )
  (entmake plin)
  (setq CR_LAYER nil)
)   


(defun m3dtray(trent)
  (setq trentdata (xdataget trent _TRAY)
	trentvdata (vtrayxdataget trent)
  )
  (if (and trentdata trentvdata)
    (progn
      
      (setq vtrydir (nth 3 trentvdata)
	    vtryadd (nth 4 trentvdata)
      )
      (if (= vtryadd 0.0)
	(progn

          (setq ptlist (bld_lw_ptlist trent)
                trpt1  (cdr (nth 0 (nth 0 ptlist)))
                trpt2  (cdr (nth 1 (nth 0 ptlist)))
                trang (angle trpt1 trpt2)
                trdist(distance trpt1 trpt2)
                trsize(nth 2 trentdata)
                trpt3 (polar trpt1 (- trang (* PI 0.5)) (* (* _PLOTSCALE trsize) 0.5))
                trpt4 (polar trpt3 trang trdist)
                trpt5 (polar trpt4 (+ trang (* PI 0.5)) (* _PLOTSCALE trsize))
                trpt6 (polar trpt5 (+ trang PI) trdist)
		3dmkelev (getvar "ELEVATION")
		3dworkelev (dxf 38 (entget trent))
          )
	  (setvar "ELEVATION" 3dworkelev)
          (pmake (list trpt3 trpt4 trpt5 trpt6) T)
	  (setvar "ELEVATION" 3dmkelev)
	  (command "extrude" (entlast) "" (* vtrydir (nth 4 trentdata)) "" )
        )
	(progn

	  (setq ptlist (bld_lw_ptlist trent)
		trpt1 (cdr (nth 0 (nth 0 ptlist)))
		trpt2 (cdr (nth 1 (nth 0 ptlist)))
		actgenang (angle trpt1 trpt2)
		trdist (distance trpt1 trpt2)
		actualdist (nth 4 trentdata)
		actualang  (nth 4 trentvdata)
		actualdir  (nth 3 trentvdata)
		trdpth     (nth 5 trentdata)
		useangle   (* actualang actualdir)
		;trpt1 (polar trpt1 (* PI -0.5) (* (nth 2 trentdata) 0.5))
	        trpt2 (polar trpt1 useangle actualdist)
	        trpt3 (polar trpt2 (+ useangle (* PI 0.5 actualdir)) (* _PLOTSCALE trdpth))
	        trpt4 (polar trpt1 (+ useangle (* PI 0.5 actualdir)) (* _PLOTSCALE trdpth))
	  )
	  (pmake (list trpt1 trpt2 trpt3 trpt4) T)
	  ;(SD)
	  (setq 3dvent (entlast)
	        3dventdata (entget 3dvent)
	        3dold  (assoc 210 3dventdata)
	        3dnew  (cons 210 (list 0.0 -1.0 -1.83691e-016))
	        3dventdata (subst 3dnew 3dold 3dventdata)
	        3dventdata (entmod 3dventdata)
	        3dventpts (nth 0 (bld_lw_ptlist 3dvent))
	        frompoint (trans (append (cdr (nth 0 3dventpts)) (list (dxf 38 3dventdata))) 3dvent 0)
	        movetopoint (append (polar trpt1 (+ actgenang (* PI -0.5)) (* 0.5 (* _PLOTSCALE (nth 2 trentdata)))) (list (dxf 38 (entget trent))))
          )
          (command "move" 3dvent "" frompoint movetopoint)
	  
          (command "rotate" 3dvent "" movetopoint (angtos actgenang 0 8))
          ;(command "move" 3dvent "" "0,0,0" (strcat "0,0," (rtos shiftfact 2 8)))
          (command "extrude" 3dvent "" (* -1 (* _PLOTSCALE (nth 2 trentdata))) "" )
	)
      )
    )
    (progn
     (if trentdata
     (progn
       (setq ptlist (bld_lw_ptlist trent)
             trpt1  (cdr (nth 0 (nth 0 ptlist)))
             trpt2  (cdr (nth 1 (nth 0 ptlist)))
             dpth (nth 5 trentdata)
             wdth (nth 2 trentdata)
             zcoord (dxf 38 (entget trent))
             genang (angle trpt1 trpt2)
             pt1 trpt1
             pt2 (polar trpt1 0.0 (distance trpt1 trpt2))
             pt3 (polar pt2 (+ (* PI 0.5) 0.0) (* _PLOTSCALE dpth))
             pt4 (polar pt1 (+ (* PI 0.5) 0.0) (* _PLOTSCALE dpth))
             _ZFLAG T
             passlist (list pt1 pt2 pt3 pt4)
             newpoint (polar trpt1 (- genang (* PI 0.5)) (* (* _PLOTSCALE wdth) 0.5))
	     newpoint (append newpoint (list zcoord))
             _USEELEV zcoord;0.0; (* -1 (cadr trpt1))
        )

        
        (pmake passlist T)
       ;(princ (dxf 10 (entget (entlast))))
       ;(setq test (entget (entlast)))
        (setq movepoint (append (dxf 10 (entget (entlast))) (list zcoord))
	;      testpt movepoint
              movepoint (trans movepoint (entlast) 0)
        )
       (princ movepoint)
        (command "move" (entlast) "" movepoint newpoint)
        (command "rotate" (entlast) "" newpoint (angtos genang 0 8))
        (command "extrude" (entlast) "" (* -1 (* _PLOTSCALE wdth)) "" )
      )
    )
   )
  )
)
(defun mtrayfit (trayfitent trayfitdata NoFlangeFlag)
	 (setq fitptbllist (bld_lw_ptlist trayfitent)
	fitptlist   (nth 0 fitptbllist)
	fitbllist   (nth 1 fitptbllist)
	fitwidth    (nth 2 trayfitdata)
	fitdpth     (nth 5 trayfitdata)
	fitalt      (nth 4 trayfitdata)
	m3delev     (getvar "ELEVATION")
	fitflange   (if (< (nth 6 trayfitdata) 0) 0.0 (nth 6 trayfitdata)) ;(nth 6 trayfitdata)
	trayfitentdata (entget trayfitent)
	fitOCS      (dxf 210 trayfitentdata)
  )
  (if NoFlangeFlag
  	  (setq fitflange 0.0)
  )
  (setvar "ELEVATION" (dxf 38 trayfitentdata))
  (xdstrip trayfitent _DOUBLE)
  (setq clay (getvar "CLAYER"))
      (if (not (tblsearch "layer" (nth 0 _MEDTRAY)))
        (progn
          (smlayer _MEDTRAY)
          (setvar "CLAYER" clay)
        )
      )
      (setq CR_LAYER (nth 0 _MEDTRAY))
  (cond
    ((= (length fitptlist) 4)
       (make_elbow fitptbllist (+ fitwidth fitflange))
       (xdrtray (entlast) trayfitent)
     )
    ((= (length fitptlist) 7)
       (make_tee fitptbllist (+ fitwidth fitflange))
       (xdrtray (entlast) trayfitent)
     )
    ((= (length fitptlist) 10)
       (make_cross fitptbllist (+ fitwidth fitflange))
       (xdrtray (entlast) trayfitent)
     )
    ((and (= (length fitptlist) 2)
	  (= 18.0 (distance (cdr (nth 0 fitptlist)) (cdr (nth 1 fitptlist)))))
       (make_re fitptbllist (+ fitwidth fitflange) (+ fitalt fitflange))
       (xdrtray (entlast) trayfitent)
     )
    ((and (= (length fitptlist) 2)
          (> (rem (distance (cdr (nth 0 fitptlist)) (cdr (nth 1 fitptlist))) 1.0) 0.0))
       (make_relr fitptbllist (+ fitwidth fitflange) (+ fitalt fitflange) trayfitent)
       (xdrtray (entlast) trayfitent)
     )
    ((vtrayxdataget trayfitent)
    	(m3dvtrayfit trayfitent)
    )
    (T nil)
    
  )
  (setvar "ELEVATION" m3delev)
)
(defun m3dtrayfit (trayfitent trayfitdata)
  (setq fitptbllist (bld_lw_ptlist trayfitent)
	fitptlist   (nth 0 fitptbllist)
	fitbllist   (nth 1 fitptbllist)
	fitwidth    (nth 2 trayfitdata)
	fitdpth     (nth 5 trayfitdata)
	fitalt      (nth 4 trayfitdata)
	m3delev     (getvar "ELEVATION")
	trayfitentdata (entget trayfitent)
  )
  (setvar "ELEVATION" (dxf 38 trayfitentdata))
  
  (cond
    ((= (length fitptlist) 4)
       (make_elbow fitptbllist fitwidth)
       (command "extrude" (entlast) "" (* _PLOTSCALE fitdpth) "")
    )
    ((= (length fitptlist) 7)
       (make_tee fitptbllist fitwidth)
       (command "extrude" (entlast) "" (* _PLOTSCALE fitdpth) "")
    )
    ((= (length fitptlist) 10)
       (make_cross fitptbllist fitwidth)
       (command "extrude" (entlast) "" (* _PLOTSCALE fitdpth) "")
    )
    ((and (= (length fitptlist) 2)
	  (= 18.0 (distance (cdr (nth 0 fitptlist)) (cdr (nth 1 fitptlist)))))
       (make_re fitptbllist fitwidth fitalt)
       (command "extrude" (entlast) "" (* _PLOTSCALE fitdpth) "")
    )
    ((and (= (length fitptlist) 2)
          (> (rem (distance (cdr (nth 0 fitptlist)) (cdr (nth 1 fitptlist))) 1.0) 0.0))
       (make_relr fitptbllist fitwidth fitalt trayfitent)
       (xdrtray (entlast) trayfitent)
       (command "extrude" (entlast) "" (* _PLOTSCALE fitdpth) "")
     )
    ((vtrayxdataget trayfitent)
     (m3dvtrayfit trayfitent)
    )
    (T nil)
    
  )
  (setvar "ELEVATION" m3delev)
  
)

(defun make_elbow (elbowdatalist trwidth)
  (setq pts (nth 0 elbowdatalist)
	bls (nth 1 elbowdatalist)
	pt1 (trans (append (cdr (nth 0 pts)) (list (getvar "ELEVATION"))) (MEDGetCurrentOCS) 1)
	pt2 (trans (append (cdr (nth 1 pts)) (list (getvar "ELEVATION"))) (MEDGetCurrentOCS) 1)
	pt3 (trans (append (cdr (nth 2 pts)) (list (getvar "ELEVATION"))) (MEDGetCurrentOCS) 1)
	pt4 (trans (append (cdr (nth 3 pts)) (list (getvar "ELEVATION"))) (MEDGetCurrentOCS) 1)
	bul1(cdr (nth 1 bls))
	ang1 (angle pt1 pt2)
	ang2 (angle pt4 pt3)
	tandist (abs (distance pt1 pt2))
	arcdata(pl_arc_info_from_buldge pt2 pt3 bul1)
	rad (nth 3 arcdata)
	apt1 (polar pt1 (- ang1 (* PI 0.5)) (* 0.5 (* _PLOTSCALE trwidth)))
        apt2 (polar pt1 (+ ang1 (* PI 0.5)) (* 0.5 (* _PLOTSCALE trwidth)))
	apt3 (polar apt1 ang1 tandist)
	apt4 (polar apt2 ang1 tandist)
        bpt1 (polar pt4 (- ang2 (* PI 0.5)) (* 0.5 (* _PLOTSCALE trwidth)))
        bpt2 (polar pt4 (+ ang2 (* PI 0.5)) (* 0.5 (* _PLOTSCALE trwidth)))
	bpt3 (polar bpt1 ang2 tandist)
        bpt4 (polar bpt2 ang2 tandist)
	mlist  (list (list apt1 nil)
                     (list apt2 nil)
                     (list apt4 bul1)
                     (list bpt3 nil)
                     (list bpt1 nil)
                     (list bpt2 nil)
                     (list bpt4 (* bul1 -1))
                     (list apt3 nil)
               )
  )
  (MEDmaketray mlist T nil (MEDGetCurrentOCS))
)

(defun make_tee (teedatalist trwidth)
  (setq pts (nth 0 teedatalist)
	bls (nth 1 teedatalist)
	pt1 (trans (append (cdr (nth 0 pts)) (list (getvar "ELEVATION"))) (MEDGetCurrentOCS) 1)
	pt2 (trans (append (cdr (nth 1 pts)) (list (getvar "ELEVATION"))) (MEDGetCurrentOCS) 1)
	pt3 (trans (append (cdr (nth 2 pts)) (list (getvar "ELEVATION"))) (MEDGetCurrentOCS) 1)
	pt4 (trans (append (cdr (nth 3 pts)) (list (getvar "ELEVATION"))) (MEDGetCurrentOCS) 1)
	pt5 (trans (append (cdr (nth 5 pts)) (list (getvar "ELEVATION"))) (MEDGetCurrentOCS) 1)
	pt6 (trans (append (cdr (nth 6 pts)) (list (getvar "ELEVATION"))) (MEDGetCurrentOCS) 1)
	bul1(cdr (nth 1 bls))
	bul2(cdr (nth 4 bls))
	ang1 (angle pt1 pt2)
	ang2 (angle pt4 pt3)
	ang3 (angle pt6 pt5)
	tandist (abs (distance pt1 pt2))
	arcdata1(pl_arc_info_from_buldge pt2 pt3 bul1)
	arcdata2(pl_arc_info_from_buldge pt4 pt5 bul2)
	rad (nth 3 arcdata1)
	apt1 (polar pt1 (- ang1 (* PI 0.5)) (* 0.5 (* _PLOTSCALE trwidth)))
        apt2 (polar pt1 (+ ang1 (* PI 0.5)) (* 0.5 (* _PLOTSCALE trwidth)))
	apt3 (polar apt2 ang1 tandist)
	bpt1 (polar pt4 (- ang2 (* PI 0.5)) (* 0.5 (* _PLOTSCALE trwidth)))
        bpt2 (polar pt4 (+ ang2 (* PI 0.5)) (* 0.5 (* _PLOTSCALE trwidth)))
	bpt3 (polar bpt1 ang2 tandist)
        bpt4 (polar bpt2 ang2 tandist)
        cpt1 (polar pt6 (+ ang3 (* PI 0.5)) (* 0.5 (* _PLOTSCALE trwidth)))
        cpt2 (polar pt6 (- ang3 (* PI 0.5)) (* 0.5 (* _PLOTSCALE trwidth)))
	cpt3 (polar cpt2 ang3 (* _PLOTSCALE tandist))
	mlist  (list (list apt1 nil)
                     (list apt2 nil)
                     (list apt3 bul1)
                     (list bpt3 nil)
                     (list bpt1 nil)
                     (list bpt2 nil)
                     (list bpt4 bul2)
                     (list cpt3 nil)
		     (list cpt2 nil)
		     (list cpt1 nil)
               )
  )
  (MEDmaketray mlist T nil (MEDGetCurrentOCS))
)
(defun make_cross (crossdatalist trwidth)
  (setq pts (nth 0 crossdatalist)
	bls (nth 1 crossdatalist)
	pt1 (trans (append (cdr (nth 0 pts)) (list (getvar "ELEVATION"))) (MEDGetCurrentOCS) 1)
	pt2 (trans (append (cdr (nth 1 pts)) (list (getvar "ELEVATION"))) (MEDGetCurrentOCS) 1)
	pt3 (trans (append (cdr (nth 2 pts)) (list (getvar "ELEVATION"))) (MEDGetCurrentOCS) 1)
	pt4 (trans (append (cdr (nth 3 pts)) (list (getvar "ELEVATION"))) (MEDGetCurrentOCS) 1)
	pt5 (trans (append (cdr (nth 5 pts)) (list (getvar "ELEVATION"))) (MEDGetCurrentOCS) 1)
	pt6 (trans (append (cdr (nth 6 pts)) (list (getvar "ELEVATION"))) (MEDGetCurrentOCS) 1)
	pt7 (trans (append (cdr (nth 8 pts)) (list (getvar "ELEVATION"))) (MEDGetCurrentOCS) 1)
	pt8 (trans (append (cdr (nth 9 pts)) (list (getvar "ELEVATION"))) (MEDGetCurrentOCS) 1)
	bul1(cdr (nth 1 bls))
	ang1 (angle pt1 pt2)
	ang2 (angle pt4 pt3)
	ang3 (angle pt6 pt5)
	ang4 (angle pt8 pt7)
	tandist (abs (distance pt1 pt2))
	arcdata1(pl_arc_info_from_buldge pt2 pt3 bul1)
	rad (nth 3 arcdata1)
	apt1 (polar pt1 (- ang1 (* PI 0.5)) (* 0.5 (* _PLOTSCALE trwidth)))
        apt2 (polar pt1 (+ ang1 (* PI 0.5)) (* 0.5 (* _PLOTSCALE trwidth)))
	apt3 (polar apt1 ang1 tandist)
	apt4 (polar apt2 ang1 tandist)
	bpt1 (polar pt4 (- ang2 (* PI 0.5)) (* 0.5 (* _PLOTSCALE trwidth)))
	bpt2 (polar pt4 (+ ang2 (* PI 0.5)) (* 0.5 (* _PLOTSCALE trwidth)))
	bpt3 (polar bpt1 ang2 tandist)
        bpt4 (polar bpt2 ang2 tandist)
        cpt1 (polar pt6 (- ang3 (* PI 0.5)) (* 0.5 (* _PLOTSCALE trwidth)))
        cpt2 (polar pt6 (+ ang3 (* PI 0.5)) (* 0.5 (* _PLOTSCALE trwidth)))
	cpt3 (polar cpt1 ang3 tandist)
	cpt4 (polar cpt2 ang3 tandist)
	dpt1 (polar pt8 (- ang4 (* PI 0.5)) (* 0.5 (* _PLOTSCALE trwidth)))
        dpt2 (polar pt8 (+ ang4 (* PI 0.5)) (* 0.5 (* _PLOTSCALE trwidth)))
	dpt3 (polar dpt1 ang4 tandist)
	dpt4 (polar dpt2 ang4 tandist)
	mlist  (list (list apt1 nil)
                     (list apt2 nil)
                     (list apt4 bul1)
                     (list bpt3 nil)
                     (list bpt1 nil)
                     (list bpt2 nil)
                     (list bpt4 bul1)
                     (list cpt3 nil)
		     (list cpt1 nil)
		     (list cpt2 nil)
		     (list cpt4 bul1)
		     (list dpt3 nil)
		     (list dpt1 nil)
		     (list dpt2 nil)
		     (list dpt4 bul1)
		     (list apt3 nil)
			   
               )
  )
  (MEDmaketray mlist T nil (MEDGETCurrentOCS))
)

(defun make_re (redatalist trwidth1 trwidth2)
  (setq pts (nth 0 redatalist)
	bls (nth 1 redatalist)
	pt1 (trans (append (cdr (nth 0 pts)) (list (getvar "ELEVATION"))) (MEDGetCurrentOCS) 1)
	pt2 (trans (append (cdr (nth 1 pts)) (list (getvar "ELEVATION"))) (MEDGetCurrentOCS) 1)
	ang1 (angle pt1 pt2)
	tandist 7.0
	apt1 (polar pt1 (- ang1 (* PI 0.5)) (* 0.5 (* _PLOTSCALE trwidth1)))
    apt2 (polar pt1 (+ ang1 (* PI 0.5)) (* 0.5 (* _PLOTSCALE trwidth1)))
	apt3 (polar apt1 ang1 (* _PLOTSCALE tandist))
	apt4 (polar apt2 ang1 (* _PLOTSCALE tandist))
    bpt1 (polar pt2 (+ ang1 (* PI 0.5)) (* 0.5 (* _PLOTSCALE trwidth2)))
    bpt2 (polar pt2 (- ang1 (* PI 0.5)) (* 0.5 (* _PLOTSCALE trwidth2)))
	bpt3 (polar bpt1 (+ PI ang1) (* _PLOTSCALE tandist))
    bpt4 (polar bpt2 (+ PI ang1) (* _PLOTSCALE tandist))
	mlist  (list (list apt1 nil)
                     (list apt2 nil)
                     (list apt4 nil)
                     (list bpt3 nil)
                     (list bpt1 nil)
                     (list bpt2 nil)
                     (list bpt4 nil)
                     (list apt3 nil)
               )
  )
  (MEDmaketray mlist T nil (MEDGetCurrentOCS))
)

(defun m3dvtrayfit(trent)
  (setq trentdata (xdataget trent _FITTING))
  (setq trvdata   (vtrayxdataget trent))
  (if (and trentdata trvdata)
    (progn
      (setq trpt         (nth 0 (bld_lw_ptlist trent))
	    trpt1        (cdr (nth 0 trpt))
	    trpt2        (cdr (nth 1 trpt))
	    actgenang   (angle trpt1 trpt2)
	    sendlist     (list (nth 2 trentdata)
			       (nth 5 trentdata)
			       (nth 1 trvdata)
			       (nth 2 trvdata)
			       (nth 3 trvdata)
			 )
      )
      (if (= (nth 3 trvdata) 1)
	(setq sendgenang PI
	      rotateang (- actgenang PI)
	      shiftfact (* _PLOTSCALE (nth 5 trentdata))
	)
	
	(setq sendgenang 0
	      rotateang actgenang
	      shiftfact 0.0
	)
      )
      (3dtrayang (nth 4 trvdata) trpt1 sendgenang sendlist)
      (setq 3dvent (entlast)
	    3dventdata (entget 3dvent)
	    3dold  (assoc 210 3dventdata)
	    3dnew  (cons 210 (list 0.0 -1.0 -1.83691e-016))
	    3dventdata (subst 3dnew 3dold 3dventdata)
	    3dventdata (entmod 3dventdata)
	    3dventpts (nth 0 (bld_lw_ptlist 3dvent))
	    frompoint (trans (append (cdr (nth 0 3dventpts)) (list (dxf 38 3dventdata))) 3dvent 0)
	    movetopoint (append (polar trpt1 (+ actgenang (* PI -0.5)) (* 0.5 (* _PLOTSCALE (nth 2 trentdata)))) (list (dxf 38 (entget trent))))
      )
      (command "move" 3dvent "" frompoint movetopoint)
      (command "rotate" 3dvent "" movetopoint (angtos rotateang 0 8))
      (command "move" 3dvent "" "0,0,0" (strcat "0,0," (rtos shiftfact 2 8)))
      (command "extrude" 3dvent "" (* (nth 3 trvdata) (* _PLOTSCALE (nth 2 trentdata))) "" )
      
     
    )
  )
)
(defun 3dtrayang (inclang intpt genang tr_dat_lst / tr_data)
  (setq trsize (nth 0 tr_dat_lst)
        trdpth (nth 1 tr_dat_lst)
        trrad  (nth 2 tr_dat_lst)
        trtan  (nth 3 tr_dat_lst)
        angpol (nth 4 tr_dat_lst)  ;-1 = -(down) and 1 = +(up)
	;angpol -1
  )
  
  (setq troff (* trdpth 0.5))
  (setq br_len  (+ trrad troff trtan)
        bul     (med_tan (* inclang 0.25))
  )
  (setq tpt1   (polar intpt genang (* _PLOTSCALE trtan))
        tcen   (polar tpt1  (+ genang (* angpol (* PI 0.5))) (* _PLOTSCALE (+ trrad troff)))
        tpt2   (polar tcen  (+ (angle tcen tpt1) (* angpol inclang)) (* _PLOTSCALE (+ trrad troff)))
        pt1    (polar intpt (- genang (* PI 0.5)) (* _PLOTSCALE troff))
        pt2    (polar pt1   genang (* _PLOTSCALE trtan))
        tpt    (polar tpt2  (+ genang (* angpol inclang)) (* _PLOTSCALE trtan))
        tang   (angle tpt2  tpt)
        pt4    (polar tpt   (- tang (* PI 0.5)) (* _PLOTSCALE troff))
        pt3    (polar pt4   (+ tang PI) (* _PLOTSCALE trtan))
        pt5    (polar tpt   (+ tang (* PI 0.5)) (* _PLOTSCALE troff))
        pt6    (polar pt5   (+ tang PI) (* _PLOTSCALE trtan))
        pt8    (polar intpt (+ genang (* PI 0.5)) (* _PLOTSCALE troff))
        pt7    (polar pt8   genang (* _PLOTSCALE trtan))
        prpt1  (be pt1 pt8)
        prpt1a (be pt2 pt7)
        prpt2  (be pt4 pt5)
        prpt2a (be pt3 pt6)


  )
  (setq mlist  (list (list pt1 nil)
                     (list pt2 (* bul angpol))
                     (list pt3 nil)
                     (list pt4 nil)
                     (list pt5 nil)
                     (list pt6 (* (- bul (* bul 2)) angpol)) 
                     (list pt7 nil)
                     (list pt8 nil)
               )
  )
  (maketray mlist T nil)
  
)




(defun pl_arc_info_from_buldge (gpt1 gpt2 gpbul)
   (setq gpang (* 4 (atan gpbul))
         gpchord(distance gpt1 gpt2)
         gpanga (- (/ 3.141592654 2.00000000) (/ gpang 2.00000000))
         gprad(/ (/ gpchord 2.00000000)(cos gpanga))
         gpdeg (* gpang (/ 180.000000000 3.141592654))
         gprtlen (* gpdeg gprad 0.017453293)
   )
   (list anga gpchord gpanga gprad gpdeg gprtlen)
)
(defun make_relr (redatalist trwidth1 trwidth2 trayfitent)
  (setq fitdata (xdataget trayfitent _FITTING))
  (setq redata (med_getdesc "FITTING" (nth 3 fitdata)))
  (if (= (strcase (substr redata 1 1)) "L")
	  (setq dirfac 1)
	  (setq dirfac -1)
  )
  (setq pts (nth 0 redatalist)
	pt1 (trans (append (cdr (nth 0 pts)) (list (getvar "ELEVATION"))) (MEDGetCurrentOCS) 1)
	pt2 (trans (append (cdr (nth 1 pts)) (list (getvar "ELEVATION"))) (MEDGetCurrentOCS) 1)
	linelen (distance pt1 pt2)
	redlen 18.0
	entang (angle pt2 pt1)
	halfalt (* (- trwidth1 trwidth2)0.5)
	halfsize2 (* trwidth2 0.5)
	sinofang (/ redlen linelen)
	cosofang (/ halfalt linelen)
	ang (* dirfac (atan (/ sinofang cosofang)))
	genang (+ entang ang)
	gpt1 (polar pt2 genang halfalt)
	genang (angle pt1 gpt1)
	tandist 7.0
  	apt1 (polar pt2 (+ genang (* dirfac (* PI 0.5))) (* _PLOTSCALE halfsize2))
	apt2 (polar apt1 (+ genang PI) (* redlen _PLOTSCALE)) 
	apt3 (polar  apt2 (- genang (* dirfac (* PI 0.5))) (* trwidth1 _PLOTSCALE))
	apt4 (polar apt3 genang (* tandist _PLOTSCALE))
	apt6 (polar pt2 (+ genang (* dirfac (* PI 1.5))) (* _PLOTSCALE halfsize2))
	apt5 (polar apt6 (+ genang PI) (* tandist _PLOTSCALE))
	mlist  (list (list apt1 nil)
                     (list apt2 nil)
                     (list apt3 nil)
                     (list apt4 nil)
                     (list apt5 nil)
                     (list apt6 nil)
               )
  )
  (MEDmaketray mlist T nil (MEDGetCurrentOCS))
)

(defun c:test()
	(setq lwpent (car (entsel))
	      size  12.0
	      alt   6.0
	)
	(if lwpent
		(progn
			(setq ptlist (bld_lw_ptlist lwpent)
			      pt1    (cdr (nth 0 (nth 0 ptlist)))
			      pt2    (cdr (nth 1 (nth 0 ptlist)))
			      hyp    (distance pt1 pt2)
			      opp    18.0
			      adj    3.0
			      entang (angle pt2 pt1)
			      sinang (/ opp hyp)
			      cosang (/ adj hyp)
			      oppfac -1 
			      ang    (* oppfac (atan (/ sinang cosang)))
			      genang (+ entang ang)
			      gpt1   (polar pt2 genang adj)
			      genang (angle pt1 gpt1)
			      npt1 (polar gpt1 (+ genang (* PI (* oppfac 0.5))) alt)
			      npt2 (polar npt1 (+ genang PI) opp) 
			      npt3 (polar  npt2 (- genang (* PI (* oppfac 0.5))) size)
			      npt4 (polar npt3 genang 7.0)
			      npt6 gpt1
			      npt5 (polar npt6 (+ genang PI) 7.0)
			)
			(setq mlist  (list (list npt1  nil)
			     (list npt2  nil)
			     (list npt3  nil)
			     (list npt4  nil)
			     (list npt5  nil)
			     (list npt6  nil)
			     )
			)
			(maketray mlist T nil)
			
		)
	)
)
			      
				 
(defun c:esolid()
  (command "erase" (ssget "X" '((0 . "3dsolid"))) "" )
)
(princ "Done.")
