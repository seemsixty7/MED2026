(princ "\rLoading MEDCon...")
(defun c:conduit ( / conent conpt conqty xdlist contag cltp ptprompt route)
    (med_cur_set "c:conduit")
    (setvar "cmdecho" 0)
    (setq cltp (getvar "celtype"))
    (ltback _LTP)
    (setq ptprompt (strcat "\nPick start point of " 
                           (clookup _CODE _CSIZE _CONDUIT) ": ")
          route (med-route-draw ptprompt nil)
    )
    (if (not route) (progn (ltback cltp) (med_ret_ok) (exit)))
    (setvar "filletrad" (* _MEDRADFAC _CSIZE _PLOTSCALE))
    ;; fillet only a 2D PLINE route (3D routes: M3D/C3D calculate the bends)
    (if (and (= _CONFILL 1) (not (cadr route)))
      (command "fillet" "p" (list (car route) (getvar "lastpoint")))
    )
    (if (not _TAGOFF)
      (setq contag (getstring T "\nConduit Tag number <NONE>: "))
      (setq contag "NONE")
    )
    (if (= contag "")
       (setq contag "NONE")
    )
    (if (not (cadr route)) (chg_tray_pl_wdth (entlast) _CONPLWIDTH))
    (setq xdlist (bld_conduit _CODE _CSIZE contag nil "T"))
    (xdatadd (entlast) xdlist)
    (ltback cltp)
    (princ)
    (med_ret_ok)
    (terpri)
)
(defun c:define ( / conent conpt conqty xdlist contag)
    (med_cur_set "c:define")
    (setvar "cmdecho" 0)
    (setvar "filletrad" (* 5 _CSIZE))
    (setq definent (car (entsel "\nSelect conduit run to define to current settings: ")))
    (xdstrip definent nil)
    (setq definentdata (entget definent))
    ;; LWPOLYLINE, 2D / 3D POLYLINE and LINE are used as they are; anything else is joined
    (if (not (member (dxf 0 definentdata) '("POLYLINE" "LWPOLYLINE" "LINE")))
      (progn
        (prompt "\nSelect all entities of conduit run (all entities must meet): ")
        (setq defineplm (ssget))
        (if (not defineplm)
           (command "pedit" definent "y" "") 
           (command "pedit" definent "y" "j" defineplm "" "")
        )
        (setq definent (entlast))
      )
    )
    (setq definen (entget definent)
          definent1 definent
    )
    (cond
      ((/= _CONFILL 1))
      ((or (= (dxf 0 definen) "LINE")
           (and (= (dxf 0 definen) "POLYLINE") (= 8 (logand 8 (dxf 70 definen)))))
        (if (/= (dxf 0 definen) "LINE")
          (princ "\n3D route (3DPOLY): no fillet step - M3D/C3D calculate the bends at each corner.")))
      (T (command "fillet" "p" definent))
    )
    (if (not _TAGOFF)
      (setq contag (getstring T "\nConduit Tag number <NONE>: "))
      (setq contag "NONE")
    )
    (if (= contag "")
       (setq contag "NONE")
    )
    (setq xdlist (bld_conduit _CODE _CSIZE contag nil nil))
    (xdatadd definent xdlist)
    (princ)
    (med_ret_ok)
    (terpri)
)
(defun c:fc( / tem)
    (med_cur_set "c:fc")
    (if _FCSIZE
      (progn
       (setq tem _FCSIZE)
       (setq _FCSIZE (getdist (strcat "\nEnter conduit size:<" (rtos _FCSIZE 4) "> ")))
      )
      (setq _FCSIZE (getdist "\nEnter conduit size number only: "))
    )
    (if (not _FCSIZE)
      (setq _FCSIZE tem)
    )
    (setvar "filletrad" (* _MEDRADFAC _FCSIZE _PLOTSCALE))
    (command "fillet")
    (med_ret_ok)
    (princ)
)
(defun c:flex( / ep pt1 pt2 pt3 pt4 pt5 sp)
   (med_cur_set "c:flex")
   (princ)
   (setq pt1 (getpoint "Enter start point of flex ")
         pt2 (getpoint "\nEnter second point of flex" pt1)
   )
   (command "insert" "1flexcon" pt1 _SC "" pt2)
   (setq pt3 (getpoint "\nEnter third point of flex" pt2)
         pt5 (getpoint "\nEnter fourth point of flex" pt3)
         pt4 (getpoint "\nEnter last point of flex" pt5)
          sp (polar pt1 (angle pt1 pt2) (* _SC 0.03125))
          ep (polar pt4 (angle pt4 pt5) (* _SC 0.03125))
   )
   (command "pline" sp pt2 pt3 pt5 ep "" "pedit" "l" "s" "w"
            (* _SC 0.015625 _PLOTSCALE) "" "insert" "" pt4 _SC "" pt5
   )
   (med_ret_ok)
   (princ)
)
(defun c:consize(/)
   (med_cur_set "c:consize")
   (if (> (setq index_val (load_dialog "MED")) 0)
      (progn
         (if (new_dialog "Med_ConSize" index_val)
            (progn 
                (set_tile (eval (strcat "size" (strcase _CLETT T))) "1")
                (action_tile "sizea" "(newsz 0.840 \"A\" 0.50)")
                (action_tile "sizeb" "(newsz 1.050 \"B\" 0.75)")
                (action_tile "sizec" "(newsz 1.315 \"C\" 1.00)")
                (action_tile "sized" "(newsz 1.660 \"D\" 1.25)")
                (action_tile "sizee" "(newsz 1.9   \"E\" 1.50)")
                (action_tile "sizef" "(newsz 2.375 \"F\" 2.00)")
                (action_tile "sizeg" "(newsz 2.875 \"G\" 2.50)")
                (action_tile "sizeh" "(newsz 3.50  \"H\" 3.00)")
                (action_tile "sizei" "(newsz 4.0   \"I\" 3.50)")
                (action_tile "sizej" "(newsz 4.50  \"J\" 4.00)")
                (action_tile "sizek" "(newsz 5.563 \"K\" 5.00)")
                (action_tile "sizel" "(newsz 6.625 \"L\" 6.00)")
                (action_tile "runcon" "(done_dialog 2)")
                (action_tile "accept" "(done_dialog 1)")
                (action_tile "cancel" "(done_dialog 0)")


                (setq result (start_dialog))
            )
         )
         (unload_dialog index_val)
         (if (= result 1)
            (newsz nil nil nil)
         )
         (if (= result 2)
          (progn
            (newsz nil nil nil)
            (c:conduit)
          )
         )

      )
   )
   (med_ret_ok)
   (princ)
)

(defun c:2break( / pt1 pt2 dist inspt)
  (med_cur_set "c:2break")
  (dblins "2break" 0)
  (med_ret_ok)
  (princ)
)
(defun c:2lcon ()
  (c:conduit)
  (chg_tray_pl_wdth (entlast) 0.0)
  (mk2lcon (entlast))
  (princ)
)
(defun c:2lflex ( / 2lent 2lpt 2lent1 2lent2 tcode)
  (smlayer _MEDDETCON)
  (setq tcode _CODE
        _CODE _FLEXTYPE
  )
  (c:conduit)
  (chg_tray_pl_wdth (entlast) 0.0)
  (setq 2lent (entlast)
        2lpt (getvar "LASTPOINT")
  )
  (command "pedit" (list 2lent 2lpt) "s" "")
  (command "offset" (* _PLOTSCALE (* _ACSIZE 0.5)) (list 2lent 2lpt) (polar 2lpt 0.785398 (* _PLOTSCALE 1.0)))
  (setq 2lent1 (entlast))
  (command (list 2lent 2lpt) (polar 2lpt 3.92699 (* _PLOTSCALE 1.0)) "")
  (setq 2lent2 (entlast))
  (chg_tray_pl_wdth 2lent1 _CONDTLPLWIDTH)
  (chg_tray_pl_wdth 2lent2 _CONDTLPLWIDTH)
  (xdr2line  2lent1 2lent2 2lent)
  (setq _CODE tcode)
  (princ)
)

(defun c:confix ()
  (mk2lcon (car (entsel "\nSelect Conduit to fix: ")))
  (princ)
)
;;
;;Conduit related functions
;;

(defun mk2lcon (mkent)
  (if (dxf -3 (entget mkent (list _CONDUIT)))
    (progn
      (if (= (dxf 0 (entget mkent)) "LWPOLYLINE")
        (progn
           (setq mklwptlist (nth 0 (bld_lw_ptlist mkent))
                 mkentpt (cdr (nth 0 mklwptlist))
                 offang (angle mkentpt (nth 1 mklwptlist))
           )
        )
        (progn
           (setq mkentpt (dxf 10 (entget (entnext mkent)))
                 offang  (angle mkentpt (dxf 10 (entget (entnext(entnext mkent)))))
           )
        )
      )
      (setq mksel   (list mkent mkentpt)
            mksz    (nth 2 (xdataget mkent _CONDUIT))
            conlett (nth 3 (getsize nil (rtos mksz 4)))
            mksz    (nth 1 (getsize nil (rtos mksz 4)))
      )

      (xdstrip mkent _DOUBLE)
      (command "offset" (* (* _PLOTSCALE mksz) 0.5) mksel
                        (polar mkentpt (+ offang (* 0.5 PI)) (* _PLOTSCALE 1.0)))
      (setq 2lent1 (entlast))
      (command mksel (polar mkentpt (- offang (* 0.5 PI)) (* _PLOTSCALE 1.0)) "")
      (setq 2lent2 (entlast))
      (chg_tray_pl_wdth 2lent1 _CONDTLPLWIDTH)
      (chg_tray_pl_wdth 2lent2 _CONDTLPLWIDTH)
      (xdr2line  2lent1 2lent2 mkent)
      (if _MEDCENLAY
        (progn
           (if (tblsearch "layer" (nth 0 _MEDCENLAY))
              (progn
                 (command "change" mkent "" "P" "LA" (nth 0 _MEDCENLAY) "")
              )
              (progn
                 (smlayer _MEDCENLAY)
                 (command "change" mkent "" "P" "LA" (nth 0 _MEDCENLAY) "")
              )
           )
        )
      )
      (if (tblsearch "layer" (nth 0 _MEDDETCON))
         (progn
            (command "change" 2lent1 2lent2 "" "P" "LA" (nth 0 _MEDDETCON) "")
         )
         (progn
            (smlayer _MEDDETCON)
            (command "change" 2lent1 2lent2 "" "P" "LA" (nth 0 _MEDDETCON) "")
         )
      )

    )
  )
  (med_ret_ok)
  (princ)
  
)
(defun dblins( dblblname ins_code / pt1 pt2 dist inspt)
  (ltback nil)
  (prompt "\nSelect lines of conduit:")
    (setq currosmode (getvar "osmode")
  	    cmdechomode (getvar "cmdecho")
  )
  (setvar "CMDECHO" 0)
  (setq pt1 (osnap (cadr (setq ent1 (entsel "\nFirst line: "))) "endpoint")
  	    pt1a (osnap pt1 "midpoint")
  )
  (setvar "lastpoint" pt1)
  (setq entdata (entget (car ent1))
        laynm (list (dxf 8 entdata) nil nil)
  )
  (smlayer laynm)

  (setq pt2 (osnap (cadr (entsel "\nSecond line:")) "perp")
        dist (abs (distance pt1 pt2))
        inspt (be pt1 pt2)
  )
  (cond
  	  ((= ins_code nil)
  	  	  (setq insang 0.0)
  	  )
  	  ((= ins_code 0)
  	  	  (setq insang (* (angle pt1 pt1a) (/ 180.0 PI)))
  	  )
  	  ((= ins_code 1)
  	  	  (setq insang (* (angle pt1a pt1) (/ 180.0 PI)))
  	  )
  )
  (setq origin-insunits (getvar "insunits"))
  (setvar "insunits" 0)
  (command "-insert" dblblname inspt dist dist insang)
  (setvar "insunits" origin-insunits)
  (setvar "osmode" currosmode)
  (setvar "cmdecho" cmdechomode)
  (princ)
)
(defun c:2away( / pt1 pt2 dist inspt)
  (med_cur_set "c:2away")
  (dblins "2away" 4)
  (med_ret_ok)
  (princ)
)
(defun c:2toward( / pt1 pt2 dist inspt)
  (med_cur_set "c:toward")
  (dblins "baseball" 5)
  (med_ret_ok)
  (princ)
)
(princ "Done.")
