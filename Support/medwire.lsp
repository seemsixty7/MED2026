(princ "\rLoadingMEDWire...")
(defun c:tstrip( / drawit pt1 apt ang num pt2 pt3 pt4 ptlist txtpt ans)
   (med_cur_set "c:tstrip")
   (setq clay (getvar "clayer"))
   (smlayer _MEDSYM)
   (while (not drawit) 
;         (setq ans (getstring (strcat "Vertical=" (rtos _TERMVER) 
;                                "; Horizontal=" (rtos _TERMHOR)
;                                "; Draw Terminals: (V/H/<D>): "
;                               )
;                    )  
;         )
         (setq ans "D")
         (cond
            ((or (= ans "") (= (strcase ans) "D"))
               (setq  pt1    (getpoint "\nLeft point of terminals: ")
                      apt    (getpoint pt1 "\nAngle to generate")
                      ang    (angle pt1 apt) 
                      num    (getint "\nNumber of terminals to generate: ")
                      pt2    (polar pt1 ang _TERMVER)
                      pt3    (polar pt2 (+ (* PI 0.5) ang) _TERMHOR)
                      pt4    (polar pt3 (+ PI ang) _TERMVER)
                      ptlist (list pt1 pt2 pt3 pt4)
                      txtpt  (be pt1 pt3)
               )
               (pmake ptlist T)
               (command "text" "m" txtpt (angtos (+ (* PI 0.5) ang) 0 8) ".")
               (setq txtss(ssadd (entlast)))
               (repeat (1- num)
                (setq  pt1    pt2
                       pt2    (polar pt1 ang _TERMVER)
                       pt3    (polar pt2 (+ (* PI 0.5) ang) _TERMHOR)
                       pt4    (polar pt3 (+ PI ang) _TERMVER)
                       txtpt  (be pt1 pt3)
                       ptlist (list pt1 pt2 pt3 pt4)
                )
                (pmake ptlist T)
                (command "text" "m" txtpt (angtos (+ (* PI 0.5) ang) 0 8) ".")
                (setq txtss(ssadd (entlast) txtss))
               )
            )
          )
          (setq drawit T)
   )
   (smlayer _MEDTEXT)
   (command "change" txtss "" "P" "LA" (nth 0 _MEDTEXT) "")
   (command "layer" "s" clay "")
   (med_ret_ok)
   (princ)
   (initget "Yes No")
   (setq ans (getkword "\nWould You like to execute CTEDIT om the terminal Text <Y>/N: "))
   (if (or (not ans) (= ans "Yes"))
     (progn
      (setq CTEDITSS txtss
            txtss nil
      )
      (C:CTEDIT)
     )
   )
)
(defun c:medline ( / conent conpt conqty xdlist contag cltp ptprompt)
    (med_cur_set "c:medline")
    (setvar "cmdecho" 0)
    (setq cltp (getvar "celtype"))
    (ltback _LTP)
    (command "pline")
    (setq ptprompt "\nPick start point:"
          conpt (getpoint ptprompt)
    )
    (command conpt)
    (while (eq 1 (getvar "cmdactive"))
         (prompt "\nPick point: ")
         (command pause)
    )
    (ltback cltp)
    (princ)
    (med_ret_ok)
    (terpri)
)
(defun c:2line()
    (med_cur_set "c:2line")
    (setvar "cmdecho" 0)
    (setq cltp (getvar "celtype"))
    (ltback _LTP)
    (command "pline")
    (setq ptprompt "\nStart Point of Double Lines: "
          conpt (getpoint ptprompt)
    )
    (command conpt)
    (while (eq 1 (getvar "cmdactive"))
         (prompt "\nPick point: ")
         (command pause)
    )
    (setq offpt (getpoint conpt "\nSelect Side to offset to: "))
    (if conpt
       (command "offset" _2LINOFF conpt offpt "")
    )
    (ltback cltp)
    (princ)
    (med_ret_ok)
    (terpri)
)

(defun c:3line()
    (med_cur_set "c:3line")
    (setvar "cmdecho" 0)
    (setq cltp (getvar "celtype"))
    (ltback _LTP)
    (command "pline")
    (setq ptprompt "\nStart Point of Triple Lines: "
          conpt (getpoint ptprompt)
    )
    (command conpt)
    (while (eq 1 (getvar "cmdactive"))
         (prompt "\nPick point: ")
         (command pause)
    )
    (setq offpt (getpoint conpt "\nSelect Side to offset to: "))
    (if conpt
      (progn
       (command "offset" (* _SC _3LINOFF) conpt offpt "")
       (command "offset" (* _SC _3LINOFF 2) conpt offpt "")
      )
    )
    (ltback cltp)
    (princ)
    (med_ret_ok)
    (terpri)
)
(princ "Done.")
