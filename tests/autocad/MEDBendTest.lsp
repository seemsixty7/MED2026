;; MEDBendTest.lsp - helpers for MEDBendTest.ps1 (loaded after MEDRouteTest.lsp)
(defun bt-3dpoly (pts / )
  (entmake '((0 . "POLYLINE") (100 . "AcDbEntity") (100 . "AcDb3dPolyline") (66 . 1) (10 0.0 0.0 0.0) (70 . 8)))
  (foreach p pts
    (entmake (list '(0 . "VERTEX") '(100 . "AcDbEntity") '(100 . "AcDbVertex") '(100 . "AcDb3dPolylineVertex")
                   (cons 10 (mapcar 'float p)) '(70 . 32))))
  (entmake '((0 . "SEQEND")))
  (setq bt-e (entlast))
  (while (/= (cdr (assoc 0 (entget bt-e))) "POLYLINE") (setq bt-e (entnext bt-e)))
  bt-e)
(defun bt-first-poly ( / e r)
  (setq e (entlast))
  e)
;; expected volume = area x (straights + bend arcs); prints radius + source
(defun bt-solid (tag e kind / r sol od len plan)
  (setq *MED3D-SKIPS* nil)
  (med3d-begin "BT")
  (setq r (med3d-run e kind))
  (med3d-end)
  (if r
    (progn
      (setq sol (car r) plan (cadr r) od (med3d-get "OD" plan) len 0.0)
      (rt-volume sol)
      (foreach p (med3d-get "PIECES" plan)
        (cond ((= (car p) "L") (setq len (+ len (distance (nth 1 p) (nth 2 p)))))
              ((= (car p) "A") (setq len (+ len (* (distance (nth 1 p) (nth 3 p)) (nth 5 p)))))))
      (princ (strcat "\n[RT] " tag ": OD " (rtos od 2 4) " R " (rtos (med3d-get "R" plan) 2 4)
                     " source " (med3d-get "RSOURCE" plan)
                     " corners " (vl-princ-to-string (mapcar '(lambda (c) (med3d-get "STATUS" c)) (med3d-get "CORNERS" plan)))
                     " pieces " (vl-princ-to-string (mapcar 'car (med3d-get "PIECES" plan)))
                     " centerline " (rtos len 2 4)
                     " expected volume " (rtos (* len pi 0.25 od od) 2 3)
                     " type " (cdr (assoc 0 (entget sol))) " layer " (cdr (assoc 8 (entget sol))))))
    (princ (strcat "\n[RT] " tag ": NONE skips " (vl-princ-to-string *MED3D-SKIPS*))))
  (princ))
(defun bt-flags ( / ss)
  (setq ss (ssget "_X" '((8 . "MED_3DFLAG") (0 . "TEXT"))))
  (princ (strcat "\n[RT] flag texts " (if ss (itoa (sslength ss)) "0")
                 (if ss (strcat " first '" (cdr (assoc 1 (entget (ssname ss 0)))) "'") "")))
  (princ))
(princ)
;; debug helper: run the short-segment check step by step
(defun bt-dbg (e / pd pl r)
  (setq pd (med3d-read-path e))
  (setq pl (med3d-plan (nth 0 pd) (nth 1 pd) (nth 2 pd) (nth 3 pd) 1.315 "CONDUIT" 6.575))
  (setq r (vl-catch-all-apply 'med3d-short-3d (list pl "X" 1.315)))
  (princ "\n[RT] SHORT3D ")
  (princ (if (vl-catch-all-error-p r) (strcat "ERR " (vl-catch-all-error-message r)) r))
  (setq r (vl-catch-all-apply 'med3d-flag-at (list '(0.0 0.0 0.0) 2.0 "t")))
  (princ "\n[RT] FLAGAT ")
  (princ (if (vl-catch-all-error-p r) (strcat "ERR " (vl-catch-all-error-message r)) "ok"))
  (princ))
