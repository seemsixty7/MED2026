(princ "\rLoading MEDDetl...")
(defun c:detail( / )
   (if (> (setq index_val (load_dialog "MED")) 0)
      (progn
         (if (new_dialog "Detail" index_val)
            (progn 
                (action_tile "light"      "(done_dialog 1)")
                (action_tile "ground"     "(done_dialog 2)")
                (action_tile "power"      "(done_dialog 3)")
                (action_tile "instrument" "(done_dialog 4)")
                (action_tile "tray"       "(done_dialog 5)")
                (action_tile "comm"       "(done_dialog 6)")
                (action_tile "jbox"       "(done_dialog 7)")
                (action_tile "poleline"   "(done_dialog 8)")
                (action_tile "cancel"     "(done_dialog 0)")
                (setq result (start_dialog))
            )
         )
         (unload_dialog index_val)
         (cond
           ((= result 1)
              (select_detail "Lighting" "LTG")
           )
           ((= result 2)
              (select_detail "Grounding" "GND")
           )
           ((= result 3)
              (select_detail "Power" "PWR")
           )
           ((= result 4)
              (select_detail "Instrument" "INS")
           )
           ((= result 5)
              (select_detail "Cable Tray" "TRY")
           )
           ((= result 6)
              (select_detail "Communication" "COM")
           )
           ((= result 7)
              (select_detail "Junction Box" "JBX")
           )
           ((= result 8)
              (select_detail "Pole Line" "PLD")
           )

         )
      )
   )
   (princ)
)

(defun select_detail(descript d_type)
   (setq RESULT_LIST (FixDetailResultList (bld_dtl_list d_type)))
   (if (> (setq index_val (load_dialog "MED")) 0)
      (progn
         (if (new_dialog "DetailInsert" index_val)
            (progn 
                (start_list "detaillist")
                (foreach det RESULT_LIST
                  (add_list (nth 1 det))
                )

                (end_list)
                (set_tile "detailtype" (strcat "Select " descript " Detail:"))
                (action_tile "detaillist" "(set_detail $value)")
                (action_tile "accept"     "(done_dialog 1)")
                (action_tile "cancel"     "(done_dialog 0)")
                (setq result (start_dialog))
            )
         )
         (unload_dialog index_val)
         (if (= result 1)
           (progn
             (do_request ITM_SELECTED)
           )
         )
      )
   )
   (princ)
)

(defun set_detail(l_index)
   (setq trim 1
         cnt  1
   )
   (while (= " " (substr l_index trim))
      (setq trim (1+ trim))
   )
   (setq l_index (substr l_index trim))
   (while (setq item (read l_index))
      (setq detl_item item)
      (while (and (/= " " (substr l_index cnt 1))
                  (/= ""  (substr l_index cnt 1))
             )
             (setq cnt (1+ cnt))
      )
      (setq l_index (substr l_index cnt))
   )
   (if (> detl_item -1)
     (progn
        (setq ITM_SELECTED (nth detl_item RESULT_LIST)
              itm_image    (nth 3 ITM_SELECTED)
        )
        (start_image "detail_sym")
        (setq max_x (dimx_tile "detail_sym")
              max_y (dimy_tile "detail_sym")
        )
        (fill_image 0 0 max_x max_y 0)
        (slide_image 0 0 max_x max_y itm_image)
        (end_image)
     )
   )
)
(defun do_request(arglist / funcfound)
  (setq layset (eval (read (nth 4 arglist)))
        attval (nth 5 arglist)
        blkname(nth 3 arglist)
        matcode(nth 0 arglist)
	_MATCODE matcode
        funcname(nth 6 arglist)
	BLNAMEGOOD nil
  )
  
  (setq t1 arglist)
  (if (/= attval "")
    (setq TAT_VAL attval)
  )
  (if (= blkname "")
     (setq blkname nil
	   BLNAMEGOOD T
     )
     (progn
       (if (findfile (strcat blkname ".dwg"))
         (setq BLNAMEGOOD T)
	 (progn
	   (if (or (= (strcase (substr funcname 1 4)) "TRAY"))
		   (setq BLNAMEGOOD T)
	   )
	 )
       )
     )
  )
  (if BLNAMEGOOD
    (progn
      (cond
    	((= funcname "opt_eq_ins")
       	   (opt_eq_ins (list (list "" (nth 0 arglist))) 1 blkname layset)
           (setq funcfound T)
        )
        ((= funcname "opt+sch")
           (opt_eq_ins (list (list "" (nth 0 arglist))) 1 blkname layset)
           (getschedule (entlast))
           (setq funcfound T)
        )
        ((= funcname "full_ins")
           (opt_eq_ins (list (list "" (nth 0 arglist))) 0 blkname layset)
           (setq funcfound T)
        )
        ((= funcname "trayhd")
           (c:trayhd)
           (setq funcfound T)
        )
        ((= funcname "trayeg")
           (c:trayeg)
           (setq funcfound T)
        )
        ((= funcname "trayep")
           (c:trayep)
           (setq funcfound T)
        )
        ((= funcname "trayhinge")
           (c:trayhinge)
           (setq funcfound T)
        )
        ((= funcname "trayhang")
           (c:trayhang)
           (setq funcfound T)
        )
     )
   )
   (progn
     (alert "Block Name not Found Aborting Function:")
   )
 )
 (setq _MATCODE nil)
    
)

(defun c:gnd()
   (select_detail "Grounding" "GND")
)
(defun c:ltg()
   (select_detail "Lighting" "LTG")
)
(defun c:pwr()
   (select_detail "Power" "PWR")
)
(defun c:ins()
   (select_detail "Instrument" "INS")
)
(defun c:try()
   (select_detail "Cable Tray" "TRY")
)
(defun c:com()
   (select_detail "Communication" "COM")
)
(defun c:jbx()
   (select_detail "Junction Box" "JBX")
)
(defun c:msc()
   (select_detail "Miscellaneous" "MSC")
)

;; this function inserts jbox hub plates and hubs as required
;; per user input but does not allow creation of jboxes that
;; are non existance

(defun jbhub(maxsz maxstr bl inspt ang / pt pt1 pt2 apt ans)
 (ltback nil)
 (setq blhub "jbhub")
 (if (<= _CSIZE maxsz)
  (progn
  (initget 1 maxstr)
  (setq ans (getkword (strcat "\nNumber of hubs " maxstr ":")))
  (if (= ans "0")
    (progn
     (setq pt (polar inspt (+ ang 1.5708) (* _PLOTSCALE 0.375)))
     (if (= bl "jbhub4")
        (setq _FITTCODE 230)
        (setq _FITTCODE 227)
     )
     (setq _TAGSUPRESS T)
     (medblkins _MEDDETFIT bl inspt (angtos ang) 1 2)
    )
  )
  (if (= ans "1")
    (progn
     (setq pt (polar inspt (+ ang 1.5708) (* _PLOTSCALE 0.375)))
     (if (= bl "jbhub4")
        (setq _FITTCODE 229)
        (setq _FITTCODE 226)
     )
     (setq _TAGSUPRESS T)
     (medblkins _MEDDETFIT bl inspt (angtos ang) 1 2)
     (smlayer _MEDDETFIT)
     (insblk (strcat blhub _CLETT) pt 1.0 (angtos ang))
    )
  )
  (if (or (and (= bl "jbhub8") (= ans "2") (< _CSIZE 2.5))
          (and (= bl "jbhub4") (= ans "2") (< _CSIZE 1.0))
      )
    (progn
     (if (= bl "jbhub8")
       (setq pt (polar inspt (+ ang 1.5708) (* _PLOTSCALE 0.375))
             pt1 (polar pt ang (* _PLOTSCALE 2.125))
             pt2 (polar pt (+ ang 3.14159) (* _PLOTSCALE 2.125))
       )
       (setq pt (polar inspt (+ ang 1.5708) (* _PLOTSCALE 0.375))
             pt1 (polar pt ang (* _PLOTSCALE 1.0625))
             pt2 (polar pt (+ ang 3.14159) (* _PLOTSCALE 1.0625))

       )
     )
     (if (= bl "jbhub4")
        (setq _FITTCODE 228)
        (setq _FITTCODE 225)
     )
     (setq _TAGSUPRESS T)
     (medblkins _MEDDETFIT bl inspt (angtos ang) 1 2)
     (smlayer _MEDDETFIT)
     (insblk (strcat blhub _CLETT) pt1 1.0 (angtos ang))
     (insblk (strcat blhub _CLETT) pt2 1.0 (angtos ang))
    )
  )
  (if (and (= ans "3") (< _CSIZE 2.0))
    (progn
     (setq pt (polar inspt (+ ang 1.5708) (* _PLOTSCALE 0.375))
           pt1 (polar pt ang (* _PLOTSCALE 2.65625))
           pt2 (polar pt (+ ang 3.14159) (* _PLOTSCALE 2.65625))
     )
     (setq _FITTCODE 224)
     (setq _TAGSUPRESS T)
     (medblkins _MEDDETFIT bl inspt (angtos ang) 1 2)
     (smlayer _MEDDETFIT)
     (insblk (strcat blhub _CLETT) pt 1.0 (angtos ang))
     (insblk (strcat blhub _CLETT) pt1 1.0 (angtos ang))
     (insblk (strcat blhub _CLETT) pt2 1.0 (angtos ang))
    )
  ) 
  (if (not pt)
   (prompt "\nInvalid number of hubs for hub size\n")
  )
 )
 (prompt "\nConduit size is to large for jbox\n")
 )
)

(princ "Done.")
