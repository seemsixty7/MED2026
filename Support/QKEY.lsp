;;Revision Comments

;;By: Clint Moore
;;Date: 03/26/1999
;;Comments
;;
;;Modified MED References for MED Command Set
;;Removed all non Plan relevant commands
;;
;==========
;;By: Clint Moore
;;Date: 01/19/1999
;;Comments
;;
;;Added GetSchedule function as requested by Mickey Pool
;;Also Revised sel_att_ent function to return nil if entity not found.
;;


;;;MED Quick key lisp file loaded at start up
;;;Users may modify this file to meet their desires
;;;Copyright Moore Design (c) 1992 - 2017
(princ "\nLoading Qkeys")

(defun c:zw()
    (command "zoom" "w"))
(defun c:zd()
    (command "zoom" "d"))
(defun c:zp()
    (command "zoom" "p") (princ))
(defun c:zv()
    (command "zoom" "v") (princ))
(defun c:ze()
    (command "zoom" "e") (princ))
(defun c:va()
    (command "'view" "r" "all") (princ))
(defun c:vr()
    (command "'view" "r"))
(defun c:ew()
    (command "erase" "w"))
(defun c:ec()
    (command "erase" "c"))
(defun c:cw()
    (command "copy" "w"))
(defun c:cc()
    (command "copy" "c"))
(defun c:mw()
    (command "move" "w"))
(defun c:mc()
    (command "move" "c"))
(defun c:rw()
    (command "rotate" "w"))
(defun c:rc()
    (command "rotate" "c"))
(defun c:st()
    (command "stretch" "crossing"))
(defun c:bf()
    (prompt "\nSelect Entity to break: ")
    (command "break" pause)
    (prompt "\nFirst Point: ")
    (command "first" pause)
    (prompt "Second Point: ")
    (command  pause)
)
(defun c:dd ( / ent)
        (setq ent (entget (car (entsel))))
        (if (or (= (dxf 0 ent) "TEXT" )(= (dxf 0 ent) "ATTDEF") (= (dxf 0 ent) "MTEXT"))
              (command "DDEDIT" (dxf -1 ent) "")
              (if (= (dxf 0 ent) "INSERT")
                  (command "DDATTE" (dxf -1 ent))
              )
        )
        (princ)
)
(defun c:mcon( / ment mdata xdlist)
   (setq ment (car (entsel "\nSelect Entity to add a conduit: "))
         mdata(entget ment)
   )
   (if (or (= (dxf 0 mdata) "POLYLINE")
           (= (dxf 0 mdata) "LWPOLYLINE")
       )
      (progn
        (setq xdlist (bld_conduit _CODE _CSIZE "NONE" nil nil))
        (xdatadd ment xdlist)
      )
      (progn
        (prompt "\nEntity selected is not a polyline")
      )
   )
)
(defun c:medcopy()
   (setq ment (car (entsel "\nSelect Entity to with Xdata to Copy: "))
         mdata(entget ment (list "MED*"))
         xdlist (dxf -3 mdata)
         cnt 0
   )
   (prompt "\nSelect Entities to copy data to:")
   (setq copyss (ssget))
   (if copyss
     (progn
      (setq num (sslength copyss))
      (while (< cnt num)
        (setq ment (ssname copyss cnt)
              mdata (entget ment)
        )
        (foreach xditm xdlist
           (if (and (/= (dxf 0 mdata) "POLYLINE")
                    (/= (dxf 0 mdata) "LWPOLYLINE")
               )
             (progn
              (setq itmtype (car xditm))
              (if (or (= _CONDUIT itmtype)
                      (= _CABLE   itmtype)
                      (= _TRAY    itmtype)
                  )
                  (progn
                    (setq xditmnew nil)
                    (setq typlist (cdr xditm)
                          typlistcnt 0
                          xditmnew (list itmtype)
                    )
                    (foreach itmdata typlist
                       (setq firstpart (cdr itmdata)
                             field (substr firstpart 1 9)
                       )
                       (if (= field "ITEM_MESR")
                          (setq itmdata (cons 1000 "ITEM_MESR=F"))
                       )
                       (setq xditmnew (append xditmnew (list itmdata)))

                    )
                    (setq xditm xditmnew)
                  )
               )
              )
           )
           (xdatadd ment xditm)
        )
        (setq cnt (1+ cnt))
      )
     )
   )
)
(defun c:mtray( / ment mdata xdlist)
   (setq ment (car (entsel "\nSelect Entity to add a tray: "))
         mdata(entget ment)
   )
   (if (or (= (dxf 0 mdata) "POLYLINE")
           (= (dxf 0 mdata) "LWPOLYLINE")
       )
      (progn
        (setq xdlist (bld_tray _TRCODE _TRSIZE "NONE" nil _TRDEPTH nil))
        (xdatadd ment xdlist)
      )
      (progn
        (prompt "\nEntity selected is not a polyline")
      )
   )
)
(defun c:mcable( / ment mdata xdlist)
   (setq ment (car (entsel "\nSelect Entity to add a cable: "))
         mdata(entget ment)
   )
   (if (or (= (dxf 0 mdata) "POLYLINE")
           (= (dxf 0 mdata) "LWPOLYLINE")
       )
      (progn
        (setq xdlist (bld_cable _CABCODE 1 "NONE" "NONE" nil nil))
        (xdatadd ment xdlist)
      )
      (progn
        (prompt "\nEntity selected is not a polyline")
      )
   )
)
(defun c:mequip( / ment mdata xdlist)
   (setq ment (car (entsel "\nSelect Entity to add equipment: "))
         mdata(entget ment)
   )
   (setq xdlist (bld_equip _EQCODE "NONE"))
   (xdatadd ment xdlist)
)
(defun c:mfit( / ment mdata xdlist)
   (setq ment (car (entsel "\nSelect Entity to add a fitting: "))
         mdata(entget ment)
   )
   (setq xdlist (bld_fitting _FITTCODE _CSIZE "NONE" nil nil))
   (xdatadd ment xdlist)
)

(defun c:qc ( / pt rad)
    (setq pt (getpoint "Center point: "))
    (while
         (setq rad (getdist pt "\nRadius of circle: "))
         (command "circle" pt rad)
    )
)

;
; C:CTAG inserts a conduit tagging block and retrieves info about conduit
; from entity selected
;

(defun c:ctag( / ctlt ctlay cctid ccten cctszl ctpt1 ctpt2 ctpt3 ctan ctlen ctinfo)
         (setq ctlt (getvar "celtype"))
         (med_cur_set "c:ctag")
         (ltback nil)
         (setq ctlay (getvar "clayer"))
         (smlayer _ECTAG)
         (setq curattdia (getvar "attdia"))
         (setq cten     (entsel "\nSelect conduit to tag: ")
               ctendata (xdataget (car cten) _CONDUIT)
         )
         (if ctendata
           (progn
             (setq ctszl (nth 2 ctendata)
                   ctid  (nth 1 ctendata)
             )
             (setq ctinfo (nth 2 (getsize nil (rtos ctszl 4))))
             (if ctinfo
               (progn
                  (setvar "ATTDIA" 0)
                  (command "insert" "contag" "pscale" (* _PLOTSCALE _SC) pause (* _PLOTSCALE _SC)
                           "" "" ctid ctinfo "" "")
                  
                  (setvar "ATTDIA" curattdia)
                  (setq ctpt1 (getvar "lastpoint")
                        ctpt2 (osnap (cadr cten) "perp")
                        ctan (/ (* (angle ctpt1 ctpt2) 180.0) pi))
                  (if (or (= 180 ctan) (= 0 ctan))
                     (setq ctlen (* _SC 0.28867513))
                     (setq ctlen (* _SC 0.25))
                  )
                  (setq ctpt3 (polar ctpt1 (angle ctpt1 ctpt2) ctlen))
                  (command "line" ctpt3 ctpt2 "")
               )
               (progn
                 (princ)
                 (prompt "Invalid selection of conduit ")
                 (princ)
               )
             )
           )
           (progn
             (princ)
             (prompt "Invalid selection of conduit ")
             (princ)
           )
         )
         (command "layer" "s" ctlay "")
         (ltback ctlt)
)
(defun c:traycon()
   (setq etype (getstring "\nSide entry or End entry <S>/E: "))
   (if (or (= etype "") (= (strcase etype) "S"))
      (setq _EQCODE (nth 0 _TRAYCON))
      (setq _EQCODE (nth 1 _TRAYCON))
   )
   (setq conlist (list 0.75 0 "B"
                       1.0  1 "C"
                       1.5  2 "E"
                       2.0  3 "F"
                       2.5  4 "G"
                       3.0  5 "H"
                       4.0  6 "J"
                 )
   )
   (setq con    (car (entsel "\nSelect conduit: "))
         data   (xdataget con _CONDUIT)
         consz  (nth 2 data)
         contg  (nth 1 data)
         endlist(member consz conlist)
         addmt  (nth 1 endlist)
         lalet  (nth 2 endlist)
         _EQCODE(+ _EQCODE addmt)
   )
   (smlayer (cons (strcat lalet "con") _CON))
   (medblkins nil "tray2con" nil nil _SC 9)
   (setq ent (entlast)
         xdlist (bld_equip _EQCODE contg)
   )
   (xdatadd ent xdlist)

   (princ)
)
(defun c:trayep()
   (trayepg_hd "trayep" "traye_pg" _MEDTRAY nil 0.0125 _TRAYEP)
   (princ)
)
(defun c:trayeg()
   (trayepg_hd "traye_pg" "traye_pg" _MEDCENLAY nil 0 _TRAYEG)
   (princ)

)
(defun c:trayhd( / instr opeqlst eqdef)
   (trayepg_hd "trayhd" "trayhd" _MEDCENLAY nil 0 _TRAYHD)
   (princ)
)

(defun trayepg_hd (blname1 blname2 mainlay angpt mwidth hd_list)
   (setq atmd (getvar "attdia")
         info nil
         cnt 0
         num 1
   )
   (setq opeqlst nil
         instr ""
   )
   (foreach itm hd_list
     (setq desc (nth 1 (med_detail itm))
           instr (strcat instr desc " ")
           opeqlst (append opeqlst (list (list desc itm)))
     )
   )
   (setq eqdef (car (nth 0 opeqlst)))

   (if (> (length hd_list) 1)
     (progn
       (initget instr)
       (if TAT_VAL
           (setq eqsel TAT_VAL)
           (setq eqsel (getkword (strcat "\nEnter Detail " instr "<" eqdef ">: ")))
       )
       (if (or (not eqsel) (= eqsel eqdef))
         (setq eqsel eqdef)
       )
     )
     (progn
        (setq eqsel eqdef)
     )
   )
   (setq TAT_VAL eqsel)
   (if _MATCODE
     (setq _EQCODE _MATCODE)
     (setq _EQCODE (cadr (assoc eqsel opeqlst)))
   )
   (setq eppt (getpoint "\nSelect Point for insertion: "))
   (if (not angpt)
      (progn
        (setq angpt(getangle eppt "\nRotation: "))
        (if (not angpt)
          (setq angpt (angle eppt (polar eppt 0.0 0.125)))
        )
      )
      (progn
        (setq angpt(osnap eppt "END")
              angpt(angle eppt angpt)
              angpt(+ angpt (* PI 0.5))
        )
      )
   )
   (setq epss (ssget "C" eppt eppt)
         num  (sslength epss)
   )
   (while (and (not info) (< cnt num))
    (if (< cnt num)
     (progn
       (setq ent  (ssname epss cnt)
                 info (xdataget ent _TRAY)
             cnt  (1+ cnt)
       )
     )
    )
   )
   (setq size (+ (nth 2 info) (nth 7 info))
             trtag (nth 1 info)
             ipt1 (polar eppt angpt (* size 0.5))
             ipt2 (polar eppt (+ angpt PI) (* size 0.5))
   )
   (smlayer _ZEROLAY)
   (setvar "attdia" 0)
   (medblkins nil blname1 ipt1 (* angpt (/ 180 PI)) _SC -1)
   (if TAT_VAL
       (progn
          (setq ent (entlast)
                val (sel_att_ent ent "DETNUM" TAT_VAL)
                TAT_VAL nil
          )
        )
   )
   (if blname2
    (progn
      (medblkins nil blname2 ipt2 (* (+ angpt PI) (/ 180 PI)) _SC -1)
      (if TAT_VAL
          (progn
             (setq ent (entlast)
                   val (sel_att_ent ent "DETNUM" TAT_VAL)
                   TAT_VAL nil
             )
           )
      )
    )
   )
   (setvar "attdia" atmd)
   (smlayer mainlay)
   (command "pline" ipt1 "w" (* _SC mwidth) "" ipt2 "")
   (setq _EQCODE (MEDRemapEQCodeToProjectCode _EQCODE))
   (setq ent (entlast)
         xdlist (bld_equip _EQCODE trtag)
   )
   (xdatadd ent xdlist)

)
(defun getinst( addone ecode)
   (setq _EQCODE ecode)
   (if addone
    (progn
      (setq addlet (getstring "\nDetail <A> or B:"))
      (if (or (not addlet) (= addlet ""))
         (setq _EQCODE _EQCODE)
         (setq _EQCODE (1+ _EQCODE))
      )
    )
   )
)
(defun geninst(inprt1 inprt2 inprt3)
   (medblkins _MEDINST inprt1 nil 0.0 _SC 9)
   (setq stpt (getvar "LASTPOINT")
         ang  (getangle stpt "\nSelect loaction of additonal inst: ")
         data1(get_bl_data inprt1)
         data2(get_bl_data inprt2)
         data3(get_bl_data inprt3)
         cnt  0
   )
   (if ang
     (progn
        (cond
            ((= ang 0.0)
              (setq cnt 0)
            )
            ((= ang (* PI 0.5))
              (setq cnt 1)
            )
            ((= ang PI)
              (setq cnt 2)
            )
            ((= ang (* PI 1.5))
              (setq cnt 3)
            )
        )
        (setq dist1 (nth cnt data1)
              dist2 (+ (nth 0 data2) (nth cnt data3))
              inspt1(polar stpt ang dist1)
              inspt2(polar inspt1 ang dist2)
        )
        (medblkins _MEDINST inprt2 inspt1 (* ang (/ 180 PI)) _SC 0)
        (medblkins _MEDINST inprt3 inspt2 0.0 _SC 0)
     )
   )
)
(defun getlit(letlist ecode)
   (setq _EQCODE ecode)
   (if letlist
    (progn
      (setq klet "")
      (foreach let letlist
         (setq klet (strcat klet " " let ))
      )
      (initget 1 klet)
      (setq let (getkword (strcat "\nDetail letter (" klet ")"))
            len (length letlist)
            sublst(member let letlist)
            sublen(length sublst)
            letnum(- len sublen)
            _EQCODE (+ letnum _EQCODE)
      )
    )
   )
)
(defun c:attlay()
  (setq txtlay (nth 0 _MEDTEXT))
  (prompt "\nSelect blocks to change attribute layer: ")
  (setq attss (ssget))
  (if attss
     (progn
       (setq sslen (sslength attss)
             cnt 0
       )
       (while (< cnt sslen)
         (setq attent (ssname attss cnt)
               mattent attent
               attdata(entget attent)
         )
         (if (and (= (dxf 0 attdata) "INSERT") (assoc 66 attdata))
           (progn
              (while (/= (dxf 0 attdata) "SEQEND")
                (setq attent (entnext attent)
                      attdata(entget attent)
                      old (assoc 8 attdata)
                      new (cons 8 txtlay)
                      attdata(subst new old attdata)
                )
                (entmod attdata)
              )
              (entupd mattent)
           )
         )
         (setq cnt (1+ cnt))
      )
    )
  )
)
(defun c:wbl()
  (setq blname (getstring "\nBlock name: ")
        inspt (getpoint "\n Insertion Point: ")
        ss (ssget)
  )
  (if (tblsearch "BLOCK" blname)
    (command "block" blname "y" inspt ss "")
    (command "block" blname inspt ss "")
  )
  (setq fullfile (strcat CPELECDIR "/USER/" blname))
  (if (findfile (strcat fullfile ".dwg"))
     (command "wblock" fullfile "y" blname)
     (command "wblock" fullfile blname)
  )
)
(defun c:attrot()
  (prompt "\nSelect blocks to rotate attributes to 0 degrees: ")
  (setq attss (ssget))
  (if attss
     (progn
       (setq sslen (sslength attss)
             cnt 0
       )
       (while (< cnt sslen)
         (setq attent (ssname attss cnt)
               mattent attent
               attdata(entget attent)
               blinpt (dxf 10 attdata)
               blinptx (car blinpt)
               blinpty (cadr blinpt)
               blinptz (caddr blinpt) 
               blinpt (list blinptx blinpty 0.0)
         )
         (if (and (= (dxf 0 attdata) "INSERT") (assoc 66 attdata))
           (progn
              (while (/= (dxf 0 (entget (entnext attent))) "SEQEND")
                (setq attent (entnext attent)
                      attdata(entget attent)
                )
                (setq attins (dxf 10 attdata)
                      attinsx (car attins)
                      attinsy (cadr attins)
                      attins (list attinsx attinsy 0.0)
                      attrot (dxf 50 attdata)
                      attdist(distance blinpt attins)
                      attang (angle blinpt attins)
                      newpt  (polar blinpt (- attang attrot) attdist)
                      old_pt (assoc 10 attdata)
                      new_pt (cons 10 newpt)
                      attdata(subst new_pt old_pt attdata)
                      oldang (assoc 50 attdata)
                      newang (cons 50 0.0)
                      attdata(subst newang oldang attdata)
                )
                (entmod attdata)
              )
              (entupd mattent)
           )
         )
         (setq cnt (1+ cnt))
      )
    )
  )
)

(defun grndins(det1num det1klet det2num det2klet)
  (smlayer _MEDGRND)
  (medblkins nil "CADWELD" nil 0 _SC -1)
  (setq grndent (entlast))
  (if det1klet
    (progn
      (setq klet "")
      (foreach let det1klet
         (setq klet (strcat klet " " let ))
      )
      (initget 1 klet)
      (setq let (getkword (strcat "\nDetail letter (" klet ")"))
            len (length det1klet)
            sublst(member let det1klet)
            sublen(length sublst)
            letnum(- len sublen)
            det1num (+ letnum det1num)
      )
    )
   )
   (if det2num
     (progn
       (if det2klet
        (progn
          (setq klet "")
          (foreach let det2klet
             (setq klet (strcat klet " " let ))
          )
          (initget 1 klet)
          (setq let (getkword (strcat "\nDetail letter (" klet ")"))
                len (length det2klet)
                sublst(member let det2klet)
                sublen(length sublst)
                letnum(- len sublen)
                det2num (+ letnum det2num)
          )
        )
       )
       (setq xdlist (bld_equip (list det1num det2num) (list "DETAIL" "DETAIL")))
       (xdatadd grndent xdlist)
     )
     (progn
       (setq xdlist (bld_equip det1num "DETAIL"))
       (xdatadd grndent xdlist)
     )
  )

)
(defun grtag( cabtag / lay txt)
     (setq genang nil)
     (setq lay (getvar "clayer"))
     (smlayer _MEDTEXT)
     (command "style" "s1" nil)
     (if (not (tblsearch "BLOCK" "grab1"))
       (command "insert" "grab1" nil)
     )
     (setq lentmrk(entlast))

     (command "dim" "dimblk" "grab1" "dimasz" (* (getvar "dimasz") 0.5) "leader")
         (setq pt (getpoint "\nLeader start: ")
           pt1 pt)
         (command pt)
         (while
           (setq pt (getpoint pt "\nto: "))
       (if (not genang)
         (setq genang (angle pt1 pt))
       )
           (command pt)
         )
     (command "")
     (if (and (<= genang (* PI 1.5)) (> genang (* PI 0.5)))
        (progn
           (if (not lentmrk)
             (setq lentmrk (entnext (entlast)))
           )
           (setq entblk (entnext lentmrk)
                 entdata(entget entblk)
                 oldy   (assoc 42 entdata)
                 newy   (cons 42 (* (dxf 42 entdata) -1))
                 entdata(subst newy oldy entdata)
           )
           (entmod entdata)
        )
     )
         (setq txt cabtag)
         (command txt)
         (command "dimblk" "." "dimasz" (* (getvar "dimasz") 2.0) "exit")
         (command "layer" "s" lay "")
)

(defun grnd_ins(det1num det1klet det2num det2klet blname)
  (smlayer _MEDGRND)
  (medblkins nil blname nil nil _SC -1)
  (setq grndent (entlast))
  (if det1klet
    (progn
      (setq klet "")
      (foreach let det1klet
         (setq klet (strcat klet " " let ))
      )
      (initget 1 klet)
      (setq let (getkword (strcat "\nDetail letter (" klet ")"))
            len (length det1klet)
            sublst(member let det1klet)
            sublen(length sublst)
            letnum(- len sublen)
            det1num (+ letnum det1num)
      )
    )
   )
   (if det2num
     (progn
       (if det2klet
        (progn
          (setq klet "")
          (foreach let det2klet
             (setq klet (strcat klet " " let ))
          )
          (initget 1 klet)
          (setq let (getkword (strcat "\nDetail letter (" klet ")"))
                len (length det2klet)
                sublst(member let det2klet)
                sublen(length sublst)
                letnum(- len sublen)
                det2num (+ letnum det2num)
          )
        )
       )
       (setq xdlist (bld_equip (list det1num det2num) (list "DETAIL" "DETAIL")))
       (xdatadd grndent xdlist)
     )
     (progn
       (setq xdlist (bld_equip det1num "DETAIL"))
       (xdatadd grndent xdlist)
     )
  )

)
(defun c:mc()
  (vl-cmdf "MEDCHG")
  (princ)
)

;; This command will simplay add a supplied number of specified RE's to an Entity:
(defun c:addre()
   (setq addent (car (entsel "\nSelect Entity to Add RE'S to: "))
         sizedata (xdataget addent _FITTING)
         tagdata  (nth 1 sizedata)
         sizedata (nth 2 sizedata)
         addata (entget addent (list _FITTING))
         xadata (cadr (assoc -3 addata))
         rsizelist (list 0.50 0.75 1.00
                                 1.25 1.50 2.00
                                 2.50 3.00 3.50
                                 4.00 5.00 6.00
                   )
         redlst  (reverse (cdr (member sizedata (reverse rsizelist))))
         recode nil
         resize nil
         retag  nil
         realt  nil
         redpth nil
         re_ssize 100.0

  )
  (while (not (member re_ssize redlst))
      (prompt "\nSize may not be larger than current size.")
      (initget 1)
      (setq re_ssize (getreal "\nSize to Reduce to: "))
  )
  (setq re_qty (getint "\nNumber of Reducers to add: "))
  (if (not re_qty)
      (setq re_qty 1)
  )
  (repeat re_qty
     (setq recode (append recode (list 103))
           resize (append resize (list sizedata))
           retag  (append retag  (list tagdata))
           realt  (append realt  (list re_ssize))
           redpth (append redpth (list 0.0))
     )
  )
  (setq xbdata(bld_fitting recode resize retag realt redpth)
        xdlist (xdatappend xbdata xadata)
  )
  (xdatadd addent xdlist)
  (princ)

)
(defun c:cf()
   (if (= (getvar "clayer") (nth 0 _MEDCENLAY))
      (command "layer" "s" "0" "")
   )
   (command "layer" "off" (nth 0 _MEDCENLAY) "")
)
(defun c:cn()
   (command "layer" "on" (nth 0 _MEDCENLAY) "")
)

(defun motor(msize vert)
  (setq mtrfname (cond ((MED-UserFile "motor.dat")) ((findfile "motor.dat")))
        mtrfn    (open mtrfname "r")
  )
  (repeat 10 (read-line mtrfn))
  (setq mtrdata (read-line mtrfn))
  (while mtrdata
     (setq mtrsz (atof (substr mtrdata 1 6)))
     (if (= mtrsz msize)
       (progn
         (setq mtr_data mtrdata
               mtrdata nil
         )
       )
       (progn
         (setq mtrdata (read-line mtrfn))
       )
     )
  )
  (close mtrfn)
  (setq mtra (atof (substr mtr_data 7  8))
        mtrb (atof (substr mtr_data 15 8))
        mtrc (- (atof (substr mtr_data 23 8)) (* mtrb 0.5))
        mtrd (atof (substr mtr_data 31 8))
        mtpt (getpoint"\nStart Point: ")
  )
  (if vert
     (progn
        (command "circle" mtpt (* mtrb 0.5))
        (setq bxstpt mtpt)
     )
     (progn
       (setq mtang(getangle mtpt "\nAngle of Genration: ")
             mperc(* mtra 0.1875)
             mtrst(polar mtpt  mtang mperc)
             mtpt1(polar mtrst (+ mtang (* PI 1.5)) (* mtrb 0.5))
             mtpt2(polar mtpt1 mtang (- mtra (* mperc 2)))
             mtpt3(polar mtpt2 (+ mtang (* PI 0.5)) mtrb)
             mtpt4(polar mtpt3 (+ mtang PI) (- mtra (* mperc 2)))
             bxstpt  (polar mtpt mtang (* mtra 0.5))
       )
       (pmake (list mtpt1 mtpt2 mtpt3 mtpt4) T)
       (command "ellipse" "c" mtrst mtpt1 mtpt)
       (command "trim" mtpt2 "" (polar mtrst mtang mperc) "")
       (command "mirror" "l" "" (be mtpt3 mtpt4) (be mtpt1 mtpt2) "")
     )
  )
  (setq mtbxdir (getangle bxstpt "\nSelect Direction of Motor Box: ")
        bxpt    (polar bxstpt mtbxdir (* mtrb 0.5))
        bxpt1   (polar bxpt (+ mtbxdir (* PI 0.5)) (* mtrd 0.5))
        bxpt2   (polar bxpt1 mtbxdir mtrc)
        bxpt3   (polar bxpt2 (- mtbxdir (* PI 0.5)) mtrd)
        bxpt4   (polar bxpt3 (+ mtbxdir PI) mtrc)
  )
  (pmake (list bxpt1 bxpt2 bxpt3 bxpt4) T)
)

(defun c:wires()
  (setq stylnm _TXTSTYLE)      ;Change this to match the desired text style

  (smlayer _MEDTEXT)      ;This line reuires MED to be loaded

  (if (not oldvallist )
     (setq oldvallist "HN G")
  )
  (setq stpt   (getpoint "\nSelect point for tags: ")
        rot    (getpoint stpt "\nSelect Rotation for tags: ")
        genang (angle stpt rot)
  )
  (prompt "\nH=Hot N=Neutral Space=Spacer G=Ground S=Switchleg")

  (setq wirestr(getstring T (strcat "\nEnter Format String <" oldvallist ">: "))
        stang  (+ genang (/ PI 3.0))
        endang (+ stang PI)
        wlen   (* (* _PLOTSCALE 0.09375) _SC) ;Controls the length of the Hots
        nlen   (* (* _PLOTSCALE 0.15625) _SC) ;Controls the length of the Neutrals
        glen   (* (* _PLOTSCALE 0.15625) _SC) ;Controls the length of the Grounds
        slen   (* (* _PLOTSCALE 0.15625) _SC) ;Controls the length of the switch Leg
        sleg   (* (* _PLOTSCALE 0.0625)  _SC) ;Cnntrols the length of the leg on the switch leg
        spcr   (* (* _PLOTSCALE 0.05625) _SC) ;Spacer distance between each dash or squiggle
        cnt    0
  )
  (if (= wirestr "")
     (setq wirestr oldvallist)
  )
  (setq num (strlen wirestr)
        oldvallist wirestr
  )

  (while (< cnt num)
      (setq strval (strcase (substr wirestr (1+ cnt) 1)))
      (cond
        ((= strval "H")
          (setq spt (polar stpt stang (* 0.5 wlen))
                ept (polar spt  endang wlen)
          )
          (pmake (list spt ept) nil)
          (setq stpt (polar stpt genang spcr))
        )
        ((= strval "N")
          (setq spt (polar stpt stang (* 0.5 nlen))
                ept (polar spt  endang nlen)
                plin  '((0 . "POLYLINE"))
                vtxt1  (list (cons 0 "VERTEX") (cons 10 spt) (cons 42 0.4))
                vtxt2  (list (cons 0 "VERTEX") (cons 10 stpt) (cons 42 -0.4))
                vtxt3  (list (cons 0 "VERTEX") (cons 10 ept))
                sqend  (list (cons 0 "SEQEND"))
          )
          (entmake plin)
          (entmake vtxt1)
          (entmake vtxt2)
          (entmake vtxt3)
          (entmake sqend)
          (setq stpt (polar stpt genang spcr))
        )
        ((= strval " ")
          (setq stpt (polar stpt genang spcr))
        )
        ((= strval "G")
          (setq spt (polar stpt stang (* 0.5 glen))
                ept (polar spt  endang glen)
                txt (list (cons 0 "TEXT") (cons 1 "G")
                          (cons 10 ept) (cons 11 ept)
                          (cons 7 stylnm) (cons 50 genang)
                          (cons 40 (* 0.0625 _SC))
                          (cons 72 1) (cons 73 2)
                    )
          )
          (pmake (list spt ept) nil)
          (entmake txt)
          (setq stpt (polar stpt genang spcr))
        )
        ((= strval "S")
          (setq spt (polar stpt stang (* 0.5 slen))
                ept (polar spt  endang slen)
                npt (polar ept  genang sleg)
          )
          (pmake (list spt ept npt) nil)
          (setq stpt (polar stpt genang spcr))
        )
      )
      (setq cnt (1+ cnt))
  )
  (entmake)

)

(defun c:refdwg()
  (med_cur_set "C:REFDWG")
  (setq dwglist nil
        currlist nil
  )
  (setq lay (getvar "CLAYER"))
  (smlayer _MEDTEXT)
  (setq intpt (dxf 10 (entget (car (entsel "\nSelect Title Block: "))))
        intpt (polar intpt 0.0 (* _SC 29.4375))
        intpt (polar intpt (* PI 0.5) (* _SC 2.375))
  )
  (initget "Add New")
  (setq ans (getkword "\nAdd Refrences or New Refrences<N>: "))
  (if (= ans "Add")
    (progn
      (prompt "\nSelect Existing Reference drawings: ")
      (setq txtss (ssget)
            num   (sslength txtss)
            cnt   0

      )
      (while (< cnt num)
         (setq ent     (ssname txtss cnt)
               entdata (entget ent)
         )
         (if (= "TEXT" (dxf 0 entdata))
           (progn
              (setq ipt   (polar (dxf 11 entdata) (* PI 1.5) 0.025)
                    itm   (dxf 1 entdata)
                    ipt2  (polar ipt 0.0 (* _SC 0.375))
                    ipt2  (polar ipt2 (* PI 1.5) (* _SC 0.125))
                    ipt3  (polar ipt2 0.0 (* _SC 2.9366))
                    ipt3  (polar ipt3 (* PI 0.5) (* _SC 0.25))
                    dat1  (ssget "w" ipt2 ipt3)
              )
              (if dat1
                 (setq datlen(sslength dat1))
              )
              (if (< datlen 1)
                (progn
                  (setq dwgdesc (getdwgnm itm)
                        dwgnum itm
                        dwglist (append dwglist (list dwgnum))
                        currlist(append currlist (list (list dwgnum dwgdesc)))
                  )
                  (entdel ent)
                )
                (progn
                  (setq datent (ssname dat1 0)
                        dwgdesc (dxf 1 (entget datent))
                        dwgnum itm
                        dwglist (append dwglist (list dwgnum))
                        currlist(append currlist (list (list dwgnum dwgdesc)))
                  )
                  (entdel ent)
                  (entdel datent)
                )
              )
           )
         )
         (setq cnt (1+ cnt))
      )
    )
  )
  (while (/= (setq dwgitem(getstring T "\nDrawing Number: ")) "")
         (setq dwglist (append dwglist (list dwgitem)))
  )
  (setq dwglist (acad_strlsort dwglist)
        dwglist (reverse dwglist)
  )
  (foreach itm dwglist
     (setq pt1 (polar intpt 0.0 (* _SC 0.40894539)))
     (if (setq dwgdesc (assoc itm currlist))
        (setq dwgdesc (cadr dwgdesc))
        (setq dwgdesc (getdwgnm itm))
     )
     (setq dwgnum itm)
     (command "text" "s" "s1a" "m" intpt "" dwgnum)
     (command "text" "s" "s1a" "ml" pt1   "" dwgdesc)
     (setq intpt (polar intpt (* PI 0.5) (* _SC 0.25)))

  )
  (setvar "CLAYER" lay)
  (med_ret_ok)
  (princ)

)
(defun getdwgnm(dwgnum)
  (setq fn   (open (findfile "dwgindex.dat") "r")
        dline(read-line fn)
        dlcd (atoi (substr dline 1 16))
  )
  (while (and (/= dlcd dwgnum) dline)
    (setq dline(read-line fn))
    (if dline
       (setq dlcd (chopspace (substr dline 1 16)))
    )
  )
  (close fn)
  (if (not dline)
     (progn
       (setq dwgdesc "N/F")
     )
     (progn
       (setq dwgdesc (chopspace (substr dline 17 80)))
     )
  )
  dwgdesc
)

(defun c:planmotor()
  (initget "Horz Vertical")
  (setq ans (getkword "\nHorizontal or Vertical <H>: "))
  (if (or (not ans) (= ans "Horz"))
    (progn
      (setq vmotor nil)
    )
    (progn
      (setq vmotor T)
    )
  )
  (motor motorhp vmotor)
  (princ)
)
(defun cntrlsta( blname fcode)
  (setq oldacs _ACSIZE
        oldlet _CLETT
        oldsz  _CSIZE
        _ACSIZE 1.315
        _CLETT "C"
        _CSIZE 1.0
        _FITTCODE fcode
  )
  (medblkins _MEDFIT blname nil nil _SC 2)
  (setq _ACSIZE oldacs
        _CLETT  oldlet
        _CSIZE  oldsz
        ADDTOENT (entlast)
  )
  (princ)
)
(defun c:trayhang( / instr opeqlst eqdef)
   (setq cltp (getvar "CELTYPE"))
   (trayepg_hd "trayhang" "trayhang" _MEDTRAY nil 0.00625 _TRAYHANG)
   (command "change" "l" "" "p" "lt" H_CON "")
   (princ)
)

(defun c:traydrop()
   (trayfit (nth 0 _TRAYDROP) "Drop")
)

(defun c:trayblind()
   (trayfit (nth 0 _TRAYBLIND) "Blind")
)
(defun trayfit(tryfitcode tryprompt)
  (setq trybas (entsel (strcat "\nSelect Tray for " tryprompt ": ")))
  (if trybas
     (progn
        (setq trybas (car trybas)
              trydat (xdataget trybas _TRAY)
        )
        (if trydat
          (progn
            (setq trysiz (nth 2 trydat)
                  trydpt (nth 5 trydat)
                  xdlist (bld_fitting tryfitcode trysiz "NONE" nil trydpt)
                  drpent (entsel (strcat "\nSelect Entity To add " tryprompt " Fitting to: "))
            )
          )
          (progn
            (setq trydat (xdataget trybas _FITTING)
                  trysiz (nth 2 trydat)
                  trydpt (nth 5 trydat)
                  xdlist (bld_fitting tryfitcode trysiz "NONE" nil trydpt)
                  drpent (entsel (strcat "\nSelect Entity To add " tryprompt " Fitting to: "))
            )
          )
        )
        (if drpent
           (progn
              (setq drpent (car drpent)
                    drpdat (xdataget drpent _FITTING)
              )
              (if drpdat
                 (progn
                    (setq c-code (nth 3 drpdat)
                          c-size (nth 2 drpdat)
                          c-tag  (nth 1 drpdat)
                          c-alt  (nth 4 drpdat)
                          c-dpt  (nth 5 drpdat)
                          xdclist (bld_fitting c-code c-size c-tag c-alt c-dpt)
                          xdlist (xdatappend xdclist xdlist)
                    )
                 )
              )
              (xdatadd drpent xdlist)
              (prompt "\nXdata has been added! ")
           )
           (Prompt "\nXdata Add has Failed!!!")
        )
     )
  )
)
(defun c:strut1( / cltp clay trpt1 trpt2 trtag xdlist)
    (med_cur_set "c:strut1")
    (setvar "cmdecho" 0)
    (setq cltp (getvar "celtype"))
    (ltback _LTP)
    (setq clay (getvar "CLAYER"))
    (if _MEDCENLAY
      (progn
        (if (not (tblsearch "layer" (nth 0 _MEDCENLAY)))
          (smlayer _MEDCENLAY)
          (setvar "CLAYER" clay)
        )
        (setq CR_LAYER (nth 0 _MEDCENLAY))
      )
    )
    (setq trpt1 (getpoint "\nPick start point of double framing channel:")
          trpt2 (getpoint trpt1 "\nto point: ")
    )
    (pmake (list trpt1 trpt2) nil)
    (setq trtag "NONE")
    (setq xdlist (bld_tray (1+ _STRCODE) 1.625 trtag nil 1.625 "T"))
    (xdatadd (entlast) xdlist)
    (ltback cltp)
    (princ)
    (med_ret_ok)
    (terpri)
)
(defun c:takeoff()
;  (command "attext" "S" "lights.txt" "")
  (COMMAND "HANDLES" "ON")
  (c:BOM)
)

(defun detailtag (DetailBlockName Distance0 Distance180)
  (setvar "attreq" 1)
  (setq currosmode (getvar "OSMODE"))
  (med_cur_set "c:detag")
  (setq dt (getvar "DIMTAD")
        ne (getvar "CMDECHO")
  )
  (setvar "DIMTAD" 0)
  (setvar "CMDECHO" 0)
  (setq attdi (getvar "attdia"))
  (setvar "OSMODE" 0)
  (setq p1 (getpoint "\nFrom point: ")
        p2 (getpoint p1 "\nTo point: ")
  )
  (if (<= (car p2) (car p1))
     (setq a (* -0.5 _SC))
     (setq a (* 0.5 _SC))
  )
  (setq LeaderAngle (angle p1 p2))
  
  (smlayer _MEDTEXT)
  (if (or (= LeaderAngle PI) (= LeaderAngle 0.0))
  	  (progn
  	  	  (setq p3 p2)
  	  	  (makeleader (list p1 p2) nil (list "" _LEADSYMSIZE))
  	  	  (if (< (car p1) (car p2))
  	  	  	  (setq p4 (list (+ (car p3) distance0) (cadr p3)))
  	  	  	  (setq p4 (list (+ (car p3) distance180) (cadr p3)))
  	  	  )
  	  )
  	  (progn
  	  	  (setq p3 (list (+ (car p2) a) (cadr p2)))
  	  	  (makeleader (list p1 p2 p3) nil (list "" _LEADSYMSIZE))
  	  	  (if (< (car p2) (car p3))
  	  	  	  (setq p4 (list (+ (car p3) distance0) (cadr p3)))
  	  	  	  (setq p4 (list (+ (car p3) distance180) (cadr p3)))
  	  	  )
  	  )
  )
  (setq dent (entsel "\nSelect Entity with Detail info: "))
  (if dent
    (progn
     (if (xdataget (car dent) _EQUIP)
       (setq dent (car dent))
       (progn
         (setq dentss (ssget "C" (nth 1 dent) (nth 1 dent))
               sslen  (sslength dentss)
               cnt    0
               dent   (ssname dentss cnt)
         )
         (while (not (xdataget dent _EQUIP))
             (setq cnt (1+ cnt)
               dent (ssname dentss cnt)
             )
         )
       )
     )
     (setq data (xdataget dent _EQUIP)
           dcode(nth 2 data)
           dline(med_detail dcode)
           dnum (nth 1 dline)
           dwgn (nth 2 dline)
     )
     (setq typnum (medcount _EQUIP dcode nil nil nil nil nil nil))
     (if (not typnum)
       (setq typnum "")
       (progn
         (if (= typnum 1)
               (setq typnum "")
               (setq typnum (strcat "(TYP. " (itoa typnum) ")"))
         )
       )
     )
    )
    (progn
       (setq dnum (getstring "\nDetail Number: ")
             dwgn (getstring "\nDrawing Number: ")
             typnum (getstring "\nTypical: ")
       )
       (if (/= typnum "")
          (setq typnum (strcat "(TYP. " typnum ")"))
       )
    )
  )
  (setvar "attdia" 0)
  (command "insert" detailblockname p4 (* _PLOTSCALE _SC) "" "0" dnum dwgn typnum)
  (setvar "attdia" attdi)
  (setvar "DIMTAD" dt)
  (setvar "CMDECHO" ne)
  (setvar "OSMODE" currosmode)
)
(defun c:detag()
	(detailtag "detbub2" 0.0 0.0)
)

(defun c:detag2()
	(detailtag "dtlhd1" 0.0 -1.25)
)


(defun c:atlsc ()
  (atsched 67)
)
(defun c:atrsc ()
  (atsched 68)
)

(defun atsched( mat_id / ment mdata xdlist schedlet)
   (setq ment (car (entsel "\nSelect Entity to add Schedule data: "))
         mdata(entget ment)
         addata (entget ment (list _EQUIP))
         xadata (cadr (assoc -3 addata))


   )
   (if (not oldsched)
      (setq oldsched "W")
   )
   (setq schedlet (getstring (strcat "\nSchedule Type <" oldsched ">: ")))
   (if (= schedlet "")
      (setq schedlet oldsched)
   )
   (setq oldsched schedlet)
   (setq xdlist (bld_equip mat_id schedlet)
         xdlist (xdatappend xdlist xadata)
   )
   (xdatadd ment xdlist)
) 

(defun sel_att_ent (hd_ent at_tag new_val / sent sdata oldval newval)
 (setq sent hd_ent
       smdata (entget sent)
       sdata (list (cons 2 ""))
       at_tag (strcase at_tag)
 )
 (if (dxf 66 smdata)
  (progn
   (while (and (not (equal (dxf 0 sdata) "SEQEND"))
               (not (equal (dxf 2 sdata) at_tag))
          )
     (setq sent (entnext sent)
           sdata(entget sent)
     )
   )
   (if (= (dxf 0 sdata) "SEQEND")
     (setq sent nil)
   )
   (if new_val
      (progn
         (setq oldval (assoc 1 sdata)
               newval (cons 1 new_val)
               sdata  (subst newval oldval sdata)
         )
         (entmod sdata)
         (entupd hd_ent)
      )
   )
  )
  (setq sent nil)
 )
 sent
)

(defun c:trayhinge( / instr opeqlst eqdef)
   (trayepg_hd "trayhing" nil _MEDTRAY nil 0.00625 _TRAYHINGE)
   (princ)
)

(defun c:pb( / bpt bent)
  (while (not (setq bent (entsel "\nSelect entity to be broken: "))))
  (setq bent (car bent))
  (redraw bent 3)
  (setq bpt (getpoint "\nSelect point to be broken: "))
  (if bpt
    (progn
       (command "break" (list bent bpt) "f" bpt bpt)
    )
  )
)

(defun c:loopit()
  (smlayer _MEDTEXT)
  (setq pt1 (getpoint "\nSelect First point: ")
        pt2 (getpoint pt1 "\nSelect Second point: ")
        ang (angle pt1 pt2)
        pt3 (polar pt2 (+ ang (* PI 0.5)) (* (* _PLOTSCALE 0.09375) _SC))
        pt4 (polar pt1 (+ ang (* PI 0.5)) (* (* _PLOTSCALE 0.09375) _SC))
  )
  (pmake (list pt1 pt2 pt3 pt4) T)
  (command "fillet" "r" (* (* (* _PLOTSCALE 0.09375) _SC) 0.4999))
  (command "fillet" "p" (list (entlast) pt1))
  (command "line" (be pt2 pt3))
)

(defun c:sort()
  (setq dwglist nil
        currlist nil
  )
  (setq lay (getvar "CLAYER"))
  (smlayer _MEDTEXT)
  (setq intpt (getpoint "\nStart point:" ))
  (progn
    (prompt "\nSelect Existing Reference drawings: ")
    (setq txtss (ssget)
          num   (sslength txtss)
          cnt   0

    )
    (while (< cnt num)
       (setq ent     (ssname txtss cnt)
             entdata (entget ent)
       )
       (if (= "TEXT" (dxf 0 entdata))
         (progn
            (setq ipt   (polar (dxf 10 entdata) 0.0 (* _SC 1.5))
                  ipt   (polar ipt (* PI 1.5) (* _SC 0.0125))
                  itm   (dxf 1 entdata)
                  ipt2  (polar ipt 0.0 (* _SC 6.5))
                  ipt2  (polar ipt2 (* PI 0.5) (* _SC 0.1375))
                  dat1  (ssget "w" ipt ipt2)
            )
            (if dat1
               (setq datlen(sslength dat1))
            )
            (if (< datlen 1)
              (progn
                (setq dwgdesc "No title found"
                      dwgnum itm
                      dwglist (append dwglist (list dwgnum))
                      currlist(append currlist (list (list dwgnum dwgdesc)))
                )
                (entdel ent)
              )
              (progn
                (setq datent (ssname dat1 0)
                      dwgdesc (dxf 1 (entget datent))
                      dwgnum itm
                      dwglist (append dwglist (list dwgnum))
                      currlist(append currlist (list (list dwgnum dwgdesc)))
                )
                (entdel ent)
                (entdel datent)
              )
            )
         )
       )
       (setq cnt (1+ cnt))
    )
  )
  
  (setq dwglist (acad_strlsort dwglist))
  (foreach itm dwglist
   (setq pt1 (polar intpt 0.0 (* _SC 2.333984375)))
   (if (setq dwgdesc (assoc itm currlist))
      (setq dwgdesc (cadr dwgdesc))
      (setq dwgdesc "No title Found")
   )
   (setq dwgnum itm)
   (command "text" "s" _TXTSTYLE intpt "0" dwgnum)
   (command "text" "s" _TXTSTYLE pt1   "0" dwgdesc)
   (setq intpt (polar intpt (* PI 1.5) (* _SC 0.15625)))

  )
  (setvar "CLAYER"   lay)
  (princ)

)
(defun c:qe()
  (setq stpt (getpoint "\nSelect first point: ")
        npt  (polar stpt (* 0.5 PI) 4.15625)
        npt  (polar npt  PI 0.15625)
  )
  (command "erase" "c" stpt npt)
)
(defun qt(prefix)
  (setq txtss (ssget))
  (if txtss
    (progn
      (setq catag (getstring "\nCable Tag: ")
            catag (strcat "PART OF " prefix "-" catag)
            num (sslength txtss)
            cnt 0
      )
      (while (< cnt num)
        (setq txtent (ssname txtss cnt)
              txtdata(entget txtent)
              old    (assoc 1 txtdata)
              new    (cons 1 catag)
              txtdata(subst new old txtdata)
              cnt (1+ cnt)
        )
        (entmod txtdata)
      )
    )
  )
)
(defun itag (prefix)
  (setq stpt (getpoint "\nStartpoint for tags: ")
        tags nil
  )
  (while (/= (setq tagstr (getstring "\nTag string: ")) "")
    (setq tags (append tags (list tagstr)))
  )
  (setq tags (acad_strlsort tags))
  (foreach tag tags
    (setq brkdn (mparse tag "-" nil nil))
    (setq itm1 prefix
          itm2 (strcat (nth 0 brkdn) "-" (nth 1 brkdn))
          itm3 (nth 2 brkdn)
    )
    (setvar "attreq" 1)
    (command "insert" "itag" stpt "" "" "90" itm1 itm2 itm3)
    (command "insert" "*prtl" stpt "" "")
    (setq stpt (polar stpt 0.0 0.65))
  )
)
(defun c:qte()
  (qt "E")
)
(defun c:qta()
  (qt "A")
)
(defun c:qtr()
  (qt "R")
)
(defun c:itage()
  (itag "E")
)
(defun c:itaga()
  (itag "A")
)
(defun c:itagT()
  (itag "T")
)

(defun c:qtT()
  (qt "T")
)
(defun c:par()
  (setq ss (ssget '((0 . "TEXT"))))
  (if ss
    (progn
      (setq num (sslength ss)
            cnt 0
      )
      (while (< cnt num)
        (setq ent (ssname ss cnt)
              data(entget ent)
              val (dxf 1 data)
              old (assoc 1 data)
              new (cons 1 (strcat "(" val ")"))
              data (subst new old data)
              cnt (1+ cnt)
        )
        (entmod data)
      )
    )
  )
)
(defun c:app()
  (setq ss (ssget '((0 . "TEXT"))))
  (if ss
    (progn
      (setq tapp (getstring "\nText to append: "))
      (setq num (sslength ss)
            cnt 0
      )
      (while (< cnt num)
        (setq ent (ssname ss cnt)
              data(entget ent)
              val (dxf 1 data)
              old (assoc 1 data)
              new (cons 1 (strcat  val tapp))
              data (subst new old data)
              cnt (1+ cnt)
        )
        (entmod data)
      )
    )
  )
)

(defun c:MEDfind()
  (initget "COnduit CAble Tray Fitting Equipment")
  (setq ans (getkword "Select COnduit/Cable/Tray/Fitting/Equipment <Tray>:"))
  (if (or (= ans "") (not ans))
    (setq ans "Tray")
  )
  (cond
    ((= ans "COnduit")
       (setq mdcd _CONDUIT)
    )
    ((= ans "CAble")
       (setq mdcd _CABLE)
    )
    ((= ans "Tray")
       (setq mdcd _TRAY)
    )
    ((= ans "Fitting")
       (setq mdcd _FITTING)
    )
    ((= ans "Equipment")
       (setq mdcd _EQUIP)
    )
  )
  (setq ss1 (ssget "X" (list (list -3 (list mdcd)))))
  ss1
)


; C:TTAG inserts a tray tagging block and retrieves info about Tray
; from entity selected
;

(defun c:ttag( / ctlt ctlay cctid ccten cctszl ctpt1 ctpt2 ctpt3 ctan ctlen ctinfo
	             keyent keydata blk)
	 (setq ctlt (getvar "celtype"))
	 (setvar "attreq" 1)
	 (med_cur_set "c:ttag")
	 (ltback nil)
	 (setq ctlay (getvar "clayer"))
	 (smlayer _ECTAG)
	 (setvar "ATTDIA" 0)
	 (setq cten     (entsel "\nSelect Tray to tag: ")
	       ctelev   (dxf 38 (entget (car cten)))
	       ctendata (xdataget (car cten) _TRAY)
	 )
	 (if ctendata
	   (progn
	     (setq ctszl (nth 2 ctendata)
		   ctid  (nth 1 ctendata)
	     )
	     (setq ctinfo (strcat (nth 2 (getsize nil ctszl)) "T."))
	     (if ctinfo
	       (progn
	     (setq blk "traytag"
		   mvdist (* _SC 1.0)
		   keyent (medleader nil nil 1.0 _ECTAG)
		   keydata (bld_lw_ptlist keyent)
		   keydata (car keydata)
		   keydata (reverse keydata)
		   keypt1 (cdr (nth 1 keydata))
		   keypt2 (cdr (nth 0 keydata))
		   keyrot(angle keypt1 keypt2)
	     )
	     (setq mvdata nil)
	     (cond
	       ((or (< keyrot (* PI 0.25)) (>= keyrot (* PI 1.75)))
		  (setq keyrot 0.0
			mvdata nil
		  )
	       )
	       ((and (>= keyrot (* PI 0.25)) (< keyrot (* PI 0.75)))
		  (setq keyrot (* PI 0.5)
			mvdata nil
		  )
	       )
	       ((and (>= keyrot (* PI 0.75)) (< keyrot (* PI 1.25)))
		  (setq keyrot 0.0
			keypt2 (polar keypt2 PI (- mvdist (* _SC 0.125)))
			mvdata PI
		  )
	       )
	       ((and (>= keyrot (* PI 1.25)) (< keyrot (* PI 1.75)))
		  (setq keyrot (* PI 0.5)
			keypt2 (polar keypt2 (* PI 1.5) (- mvdist (* _SC 0.125)))
			mvdata (* PI 1.5)
		  )
	       )
	     )

	     (setq elev  (getstring (strcat "\nElevation: <" (rtos ctelev 4 2) ">:")))
	     (if (= elev "")
	       (setq elev (strcat "B.O.T. EL. " (rtos ctelev 4 2)))
	       (setq elev (strcat "B.O.T. EL. " elev))
	     )
	     (setq esystem  (getstring (strcat "\nTraySystem: ")))
	     (command "insert" blk keypt2 (* _PLOTSCALE _SC) (* _PLOTSCALE _SC) 
		      (angtos keyrot) ctid ctinfo elev esystem
	     )
	     (setq hdent (entlast)
		   atent (sel_att_ent hdent "TR_SIZE" nil)
		   atdata (entget atent)
		   txtbx (textbox atdata)
		   addon (car (cadr txtbx))
		   mvdist (+ mvdist addon)
	     )
		
	     (if mvdata
	       (progn
		 (move_attrib hdent mvdata mvdist _TR_SIZETAG)
	       )
	     )

	       )
	       (progn
	       (princ)
	       (prompt "Invalid selection of Tray ")
	       (princ)
	       )
	     )
	   )
	   (progn
	     (princ)
	     (prompt "Invalid selection of Tray ")
	     (princ)
	   )
	 )
	 (setvar "CLAYER" ctlay)
	 (ltback ctlt)
)





;
; C:IT is a command for inserting instrument ballons into drawings
; and retrirving data from instruments selected
;


(defun c:it( / info info2 itang bsize pt1 pt2)
         (med_cur_set "c:it")
         (smlayer _MEDINST)
         (setvar "ATTDIA" 0)
         (setq bsize (* _SC 0.25))
         (setq info (getstring "\nInstrument Tag: ")
               info2 (getstring "\nInstrument number: "))
         (setq pt1 (getpoint "\nPick point"))
         (command "insert" "instag" "pscale" (* _PLOTSCALE _SC ))
               (setq pt2 (getpoint pt1 "\nTag location: "))
               (command pt2 (* _PLOTSCALE _SC) "" "" info info2)
         (setq itang (angle pt2 pt1))
         (setq pt3 (list (+ (* bsize (cos itang)) (car pt2)) (+ (* bsize (sin itang))
                    (cadr pt2))))
         (command "line" pt1 pt2 "")
         (command "break" pt2 pt3)
)

(defun c:f0()
  (setq oldfrad (getvar "FILLETRAD"))
  (setvar "FILLETRAD" 0.0)
  (command "fillet")
  (while (eq 1 (getvar "cmdactive"))
       (prompt "\nPick ")
       (command pause)
  )
  (setvar "FILLETRAD" oldfrad)
)

(defun c:off2con( / mdata xdlist offent offpt)
   (if offdist
      (setq oldoffdist offdist)
      (setq oldoffdist 5.0)
   )
   (setq offent (entsel "\nSelect Entity to Offset to Conduit: "))
   (if offent
     (progn
       (setq offdist (getdist (strcat "\nDistance of offset<" (rtos oldoffdist 2 4) ">: ")))
       (if (not offdist)
	 (setq offdist oldoffdist)
       )
       (setq offpt (getpoint "\nOffset point: "))  
       (if offpt  
	 (progn  
	  (command "offset" offdist offent offpt "")  
	  (setq ment (entlast))  
	  (setq mdata (entget ment)  
		mpt  (dxf 10 mdata)  
	  )  
	  (if (/= (dxf 0 mdata) "POLYLINE")  
	    (progn  
	      (command "pedit" (list ment mpt) "y" "")  
	      (setq ment (entlast))  
	    )  
	  )  
	  (if (not (tblsearch "LAYER" (nth 0 _MCON)))  
	    (progn  
	     (setq currlay (getvar "celayer"))  
	     (smlayer _MCON)  
	     (setvar "CELAYER" currlay)  
	    )  
	  )  
	  (command "change" ment "" "p" "la" (nth 0 _MCON) "")  
	  (setq mdata(entget ment))  
	       (setq xdlist (bld_conduit _CODE _CSIZE "NONE" nil nil))  
	  (xdatadd ment xdlist)  
	 )  
       )  
     )
   )
)



(defun c:bc()
  (c:boxcloud)
)
(defun c:atc()
  (c:attcopy)
)

(defun c:hand()
  (setq handval (getstring "\Enter Handle: "))
  (if (handent handval)
    (command "copy" (handent handval) "")
    (prompt "Handle not found!")
  )
)

(defun getschedule (getschent / detnument detnuminfo detailinfo xdlist curxdata)
  (setq detnument  (sel_att_ent getschent _SCHEDATT nil))
  (if detnument
    (progn
      (setq detnumdata (entget detnument)
	    detnuminfo (dxf 1 detnumdata)
            detailinfo (med_detail detnuminfo)
            xdlist     (bld_equip (nth 0 detailinfo) "NONE")
	    curxdata   (car (dxf -3 (entget getschent (list _EQUIP))))
	    xdlist     (xdatappend xdlist curxdata)
	
      )
      (xdatadd getschent xdlist)
    )
  )
)

(defun c:blk2byl()
	(load "blk2byl")
	(C:BLK2BYL)
)

(defun c:T1Thin ()
   (med_text "T1Thin" nil)
)

;this command will simply Label all tray elevations.
(defun c:ttags( / ctlt ctlay cctid ccten cctszl ctpt1 ctpt2 ctpt3 ctan ctlen ctinfo
	         keyent keydata blk)
	 (setq txtstylname "T1") ; Set Text Stylle Name Here
	 (setq ctlt (getvar "celtype"))
	 (setvar "attreq" 1)
	 (med_cur_set "c:ttag")
	 (ltback nil)
	 (setq ctlay (getvar "clayer"))
	 (smlayer _ECTAG)
	 (setvar "ATTDIA" 0)
	 (setq ctss (ssget (list (cons 0 "LWPOLYLINE") (cons -3 (list (list _TRAY))))))
	 (if ctss
		 (progn
			 (setq ctsslen (sslength ctss)
				   ctcnt 0
			 )
			 (while (< ctcnt ctsslen)
				 (setq cten (ssname ctss ctcnt)
					   ctelev   (dxf 38 (entget cten))
					   ctptlist (bld_lw_ptlist cten)
					   ctpt1    (cdr (nth 0 (car ctptlist)))
					   ctpt2    (cdr (nth 1 (car ctptlist)))
					   ctendata (xdataget cten _TRAY)
					   cttextpt (be ctpt1 ctpt2)
					   cttextro (angle ctpt1 ctpt2)
					   ctszl (nth 2 ctendata)
					   ctid  (nth 1 ctendata)
					   ctinfo (strcat (nth 2 (getsize nil ctszl)) " TRAY B.O.T EL.=")
					   ctcnt (1+ ctcnt)
				 )
				 (if (= cttextro PI)
					 (setq cttextro 0.0)
				 )
				 (if (= cttextro (* PI 1.5))
					 (setq cttextro (* PI 0.5))
				 )
				 (setvar "elevation" ctelev)
				 (command "text" "s" txtstylname cttextpt (angtos cttextro 1 4) (strcat ctinfo (rtos ctelev 4 2)))
			)
		)
	 )
	 (command "layer" "s" ctlay "")
	 (ltback ctlt)
)
(defun c:telev( / ctlt ctlay cctid ccten cctszl ctpt1 ctpt2 ctpt3 ctan ctlen ctinfo
	         keyent keydata blk)
	 ;(setq txtstylname "T1") ; Set Text Stylle Name Here
	 (setq txtstydata (assoc "T1" MED_TXT_STYLE_MAP)
		  txtstylname (cadr txtstydata)
	 )
	 (setq ctlt (getvar "celtype"))
	 (setq currenttab (getvar "ctab"))
	 (setvar "attreq" 1)
	 (med_cur_set "c:telev")
	 (ltback nil)
	 (setq ctlay (getvar "clayer"))
	 (smlayer _ECTAG)
	 (setvar "ATTDIA" 0)
	 (if (/= currenttab "Model")
		 (command "mspace")
	 )
	 (setq cten (nentsel "\nSelect Tray CenterLine" )
		   cten (car cten)
	 )
	 (if (/= currenttab "Model")
		 (command "pspace")
	 )
	 (if cten
		 (progn
			(setq ctelev   (dxf 38 (entget cten))
				  ctendata (xdataget cten _TRAY)
				  cttextpt (getpoint "\nSelect Point for Text Placement: ")
				  ctszl (nth 2 ctendata)
				  ctid  (nth 1 ctendata)
				  ctinfo (strcat (nth 2 (getsize nil ctszl)) " TRAY B.O.T. ELEV.=")
			)
			(setvar "elevation" ctelev)
			(setq cttextro (- 0.0 (getvar "viewtwist")))
			(command "text" "s" txtstylname cttextpt (angtos cttextro 2 4) (strcat ctinfo (rtos ctelev 4 2)))
		)
	 )
	 (command "layer" "s" ctlay "")
	 (ltback ctlt)
)
