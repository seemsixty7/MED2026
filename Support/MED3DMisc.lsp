(princ "\rLoading MED3DMisc...")
;; TODO(MEDProperties EQUIPMENT): no BOM-driven 3D equipment exporter yet.
;; When one exists, stamp with: (MEDStamp3DFromBom solidEnt sourceEquipEnt "EQUIPMENT" nil)
;; 3DJBOX below is freeform (no source MED_EQUIP) — do not invent a fake exporter.
;;;This is the controlliong factor for the offset from the jbox edge
(setq MED_JBoxDoorOffset 1.0)
;;;This is the depth of the actual door
(setq MEDJBoxDoorDepth 1.0)
(defun c:3DJbox()
	(setq JBoxStartPoint (getpoint "\nInsertion Point (Left Bottom Front Corner): ")
		  JboxEndPoint   (getpoint JboxStartPoint "\nAngle of Generation (Face Alignment): ")
	)
	(if JBoxStartPoint
		(progn
			(if med-snap-off (med-snap-off)) ; snaps off for the pline/extrude/union build only (the picks above keep the user's osnaps)
			(setq JBoxHeight (getreal "\nJBox Height: ")
				  JBoxWidth  (getreal "\nJBox Width: ")
				  JBoxDepth  (getreal "\nJBox Depth: ")
				  JboxGenAngle (angle JBoxStartPoint JBoxEndPoint)
			)
			(setq JBPt2 (polar JboxStartPoint JBoxGenAngle JBoxWidth)
				  JBPt3 (polar JBPt2 (+ JBoxGenAngle (* 0.5 PI)) JBoxDepth)
				  JBPt4 (polar JBPt3 (+ JboxGenAngle PI) JBoxWidth)
			)
			(command "pline" JboxStartPoint JbPt2 JBPt3 JBPt4 "c")
			(command "extrude" "l" "" JboxHeight)
			(setq BoxEnt (entlast))
			;(setq CurrElev (getvar "ELEVATION"))
			;(setvar "ELEVATION" (+ CurrElev MED_JBoxDoorOffset))
			(setq DoorStartPoint (polar JBoxStartPoint JboxGenAngle MED_JboxDoorOffset)
				  DoorStartPoint (list (car DoorStartpoint) (cadr DoorStartPoint) (+ (caddr DoorStartPoint) MED_JboxDoorOffset))
				  DSPt2 (polar DoorStartPoint (- JBoxGenAngle (* 0.5 PI)) MED_JboxDoorOffset)
			      DSPt3 (polar DSPt2 JboxGenAngle (- JboxWidth (* MED_JboxDoorOffset 2.0)))
			      Dspt4 (polar DsPt3 (+ JBoxGenAngle (* 0.5 PI)) MED_JBoxDoorOffset)
			)
			(command "pline" DoorStartPoint DSPt2 DSPt3 DSPt4 "c")
			(command "extrude" "l" "" (- JboxHeight (* MED_JboxDoorOffset 2.0)))
			(setq DoorEnt (entlast))
			(command "union" BoxEnt DoorEnt "")
			(if med-snap-restore (med-snap-restore))
			;(setvar "ELEVATION" CurrElev)
		)
	)
)
(princ "Done.")
