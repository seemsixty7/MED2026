(princ "\rLoading MED3DTrayFunctions (sbfix 2026-10-28)...")
;(setq MED_TRAY_MATERIALWIDTH 0.125) ; Aluminum Tray
;(setq MED_TRAY_MATERIALWIDTH 0.25) ; Fiberglass Tray
;(setq MED_TRAY_TYPEOVERRIDE (list 0.0 1.5 1.5));Use this to set tray forced to Fiberglass Tray Shifts base up and uses C Frames on both sides
(setq MED_TRAY_RUNGSPACING 9.0) ; Planning to use this for Adding Rungs

;;; ---- Flange resolution (shared by every 3D tray/fitting/ladder rail builder) ----
;;; Rails fall into the thin no-lip web profile whenever |flange| < 2*t.
;;; Entities whose stored #ITEMFLNG is missing/0 (fittings default it to 0.0 in
;;; bld_fitting; older runs never got one) therefore came out as flat sheets.
;;; MED_TRAY_DEFAULTFLANGE (default _TRAYFLANGE, else 1.5) is used instead.
;;; Set MED_TRAY_DEFAULTFLANGE to 0.0 to get the old flat-web behavior back.
;;; MED_TRAY_FLANGEDEBUG T prints what each rail used.
(if (not MED_TRAY_DEFAULTFLANGE)
  (setq MED_TRAY_DEFAULTFLANGE (if (and (numberp _TRAYFLANGE) (/= _TRAYFLANGE 0.0)) _TRAYFLANGE 1.5)))
(defun MED3D-rawFlange (ent app / ed xd v)
  ;; Reads "#ITEMFLNG=" straight from xdata (no positional index).
  (if (and ent (setq ed (entget ent (list app))) (setq xd (assoc -3 ed)))
    (foreach pr (cdr (car (cdr xd)))
      (if (and (= (car pr) 1000) (= (type (cdr pr)) 'STR)
               (= (substr (cdr pr) 1 10) "#ITEMFLNG="))
        (setq v (atof (substr (cdr pr) 11))))))
  v)
(defun MED3D-effFlange (f / mt)
  (setq mt (if (numberp MED_TRAY_MATERIALWIDTH) MED_TRAY_MATERIALWIDTH 0.125))
  (cond ((and (numberp f) (>= (abs f) (* 2.0 mt))) f)
        ((and (numberp MED_TRAY_DEFAULTFLANGE) (>= (abs MED_TRAY_DEFAULTFLANGE) (* 2.0 mt)))
         MED_TRAY_DEFAULTFLANGE)
        ((numberp f) f)
        (T 0.0)))
(defun MED3D-flangeFor (ent app posval / raw f)
  (setq raw (MED3D-rawFlange ent app)
        f   (MED3D-effFlange (if raw raw posval)))
  (if MED_TRAY_FLANGEDEBUG
    (princ (strcat "\nMED3D flange " (if ent (cdr (assoc 5 (entget ent))) "?")
                   " stored=" (if raw (rtos raw 2 3) "nil")
                   " pos=" (if (numberp posval) (rtos posval 2 3) "nil")
                   " used=" (rtos f 2 3))))
  f)

(defun MEDDraw3DTray (TrayDataList UCSData / TrayPoint1 TrayPoint2 TrayWidth TrayDepth TrayFlange TrayBaseEnt TrayFlangeEnt1 TrayFlangeEnt2) ; List includes StartPoint EndPoint Width Depth Flange
	(setq TrayPoint1 (nth 0 TrayDataList)
		  TrayPoint2 (nth 1 TrayDataList)
		  TrayWidth  (nth 2 TrayDataList)
		  TrayDepth  (nth 3 TrayDataList)
		  TrayFlange (if MED_TRAYTYPEOVERRIDE (nth 0 MED_TRAYTYPEOVERRIDE) (nth 4 TrayDataList))
		  ;TrayAngle  (angle TrayPoint1 TrayPoint2)
		  TrayBaseEnt (MEDBuild3DTrayBase TrayDataList UCSData) 
		  TrayFlangeEnt1 (MEDBuild3DTrayFlange TrayDataList 1.0 UCSData)
		  TrayFlangeEnt2 (MEDBuild3DTrayFlange TrayDataList -1.0 UCSData)
    )
    (command "union" TrayBaseEnt TrayFlangeEnt1 TrayFlangeEnt2 "")
    TrayBaseEnt ; surviving 3DSOLID after UNION
)
(defun c:traytest()
	(MEDConvertTrayto3d (car (entsel)))
)
(defun MEDConvertTrayTo3D(TrayEntity / TrayPoint1 TrayPoint2 Tray3DEnt TrayTag TraySize TrayCode TrayDist TrayLen TrayDesc TraySizeStr)
	(setq TrayEntityData (entget TrayEntity)
		  TrayEntityUCSData (dxf 210 TrayentityData)
	)
	(if (equal (dxf 210 TrayEntityData) (list 0.0 0.0 1.0))
		(command "UCS" "")
		(command "ucs" "OB" trayentity)
	)
	(setq TrayPointlist (bld_lw_ptlist TrayEntity)
		  TrayPointList (car TrayPointlist)
		  TrayEntityPoint1 (append (cdr (nth 0 TrayPointlist)) (list (cdr (assoc 38 TrayEntityData))))
		  TrayEntityPoint1 (trans TrayEntityPoint1 TrayEntityUCSData 1) 
		  TrayEntityPoint2 (append (cdr (nth 1 Traypointlist)) (list (cdr (assoc 38 TrayEntityData))))
		  TrayEntityPoint2 (trans TrayEntityPoint2 TrayEntityUCSData 1)
		  TrayMEDData (xdataget TrayEntity _TRAY)
		  TrayUCSData (dxf 210 TrayEntityData)
	)


	(setq Tray3DEnt
	  (MEDDraw3DTray (list  TrayEntityPoint1
						  TrayEntityPoint2
			             (nth 2 TrayMEDData) ; Width
			             (nth 5 TrayMEDData) ; Depth
			             (MED3D-flangeFor TrayEntity _TRAY (nth 7 TrayMEDData)) ; FlangeSize
			       )
					TrayUCSData
	  )
	)
	;; Attach MEDProperties (3D ID only, not BOM) from source MED_TRAY + geometry length
	(if (and Tray3DEnt TrayMEDData)
	  (progn
	    (setq TrayDist (nth 4 TrayMEDData)
	          TrayLen  (if (and TrayDist (numberp TrayDist) (/= TrayDist 0.0))
	                       TrayDist
	                       (distance TrayEntityPoint1 TrayEntityPoint2))
	    )
	    (MEDStamp3DFromBom Tray3DEnt TrayEntity "TRAY" (rtos TrayLen 2 4))
	  )
	)
	Tray3DEnt
)
		  
(defun MEDBuild3DTrayBase (MB3DTB_TrayData TrayUCSData / TrayPoint1 TrayPoint2 TrayAngle)
	(setq TrayPoint1 (nth 0 MB3DTB_TrayData)
		  TrayPoint2 (nth 1 MB3DTB_TrayData)
		  CheckAngle (angle TrayPoint1 TrayPoint2)
		  ExtrudeDir 1
	)
	;(if (not (equal UCSData (list 0.0 0.0 1.0)))
	;	(setq TrayPoint1 (trans TrayPoint1 TrayUCSData 1)
	;		  TrayPoint2 (trans TrayPoint2 TrayUCSData 1)
	;		  ExtrudeDir (if (or (<= CheckAngle (* PI 0.5)) (> CheckAngle (* PI 1.5))) -1 1)
	;	)
	;)
	(setq t1 traypoint1 t2 traypoint2)
	(setq TrayWidth  (nth 2 MB3DTB_TrayData)
		  TrayAngle  (angle TrayPoint1 TrayPoint2)
		  TrayBasePoint1 (polar TrayPoint1 (+ TrayAngle (* PI 0.5)) (* TrayWidth 0.5))
		  TrayBasePoint2 (polar TrayPoint1 (+ TrayAngle (* PI -0.5)) (* TrayWidth 0.5))
		  TrayBasePoint3 (polar TrayPoint2 (+ TrayAngle (* PI -0.5)) (* TrayWidth 0.5))
		  TrayBasePoint4 (polar TrayPoint2 (+ TrayAngle (* PI 0.5)) (* TrayWidth 0.5))
    )
    ;(command "UCS" "")
    (command "3DPOLY" TrayBasePoint1 TrayBasePoint2 TrayBasePoint3 TrayBasePoint4 "C")
    (command "Extrude" "l" "" (* MED_TRAY_MATERIALWIDTH ExtrudeDir)) 
    (setq TrayReturnEntity (entlast))
)
(defun MEDBuild3DTrayFlange (MB3DTF_TrayData MB3DTF_FlipValue UCSData / TrayPoint1 TrayPoint2) ;Flip value is 1.0 normal opposite is -1
	(setq TrayPoint1 (nth 0 MB3DTF_TrayData)
		  TrayPoint2 (nth 1 MB3DTF_TrayData)
		  TrayWidth  (nth 2 MB3DTF_TrayData)
		  TrayDepth  (nth 3 MB3DTF_TrayData)
		  TrayFlange (MED3D-effFlange (nth 4 MB3DTF_TrayData))
		 ; UCSPoint1 (trans TrayPoint1 UCSData 0)
		 ; UCSPoint2 (trans TrayPoint2 UCSData 0)
		 ; UCSPoint3 (polar UCSPoint1 (+ (angle UCSPoint1 UCSPoint2) (* PI 0.5)) 1.0)
	)
	;(if (equal (dxf 210 TrayEntityData) (list 0.0 0.0 1.0))
	;	(command "UCS" "")
	;	(progn
	;		(command "UCS" "" "UCS" "n" "3p"  UCSPoint1 UCSPoint2 UCSPoint3)
	;		(setq TrayPoint1 (trans UCSPoint1 0 1)
	;			  TrayPoint2 (trans UCSPoint2 0 1)
	;		)
	;	)
	;)
	(setq TrayLength (distance TrayPoint1 TrayPoint2)
		  TrayAngle  (angle TrayPoint1 TrayPoint2)
		  TrayBasePoint1 (polar TrayPoint1 (+ TrayAngle (* MB3DTF_FlipValue PI 0.5)) (* TrayWidth 0.5))
	)
	(if (< TrayFlange (* 2.0 MED_TRAY_MATERIALWIDTH))
		(progn
			(setq TrayFlangePoint1 (polar TrayBasePoint1 (+ TrayAngle (*  MB3DTF_FlipValue PI 0.5)) MED_TRAY_MATERIALWIDTH)
				  TrayFlangePoint2 (list (nth 0 TrayFlangePoint1) (nth 1 TrayFlangePoint1) (+ TrayDepth (nth 2 TrayFlangePoint1)))
				  TrayFlangePoint3 (polar TrayFlangePoint2 (+ TrayAngle (* PI  MB3DTF_FlipValue -0.5)) MED_TRAY_MATERIALWIDTH)
			)
			(command "3DPOLY" TrayBasePoint1 TrayFlangePoint1 TrayFlangePoint2 TrayFlangePoint3 "C")
		)
		(progn
			(setq TrayFlangePoint1 (polar TrayBasePoint1 (+ TrayAngle (*  MB3DTF_FlipValue PI 0.5)) (* TrayFlange 0.5))
				  TrayFlangePoint2 (list (nth 0 TrayFlangePoint1) (nth 1 TrayFlangePoint1) (+ MED_TRAY_MATERIALWIDTH (nth 2 TrayFlangePoint1)))
				  TrayFlangePoint3 (polar TrayFlangePoint2 (+ TrayAngle (* PI  MB3DTF_FlipValue -0.5)) (- (* TrayFlange 0.5) MED_TRAY_MATERIALWIDTH))
				  TrayFlangePoint4 (list (nth 0 TrayFlangePoint3) (nth 1 TrayFlangePoint3) (+ (- TrayDepth (* 2.0 MED_TRAY_MATERIALWIDTH)) (nth 2 TrayFlangePoint3)))
				  TrayFlangePoint5 (list (nth 0 TrayFlangePoint1) (nth 1 TrayFlangePoint1) (+ (- TrayDepth MED_TRAY_MATERIALWIDTH) (nth 2 TrayFlangePoint1)))
				  TrayFlangePoint6 (list (nth 0 TrayFlangePoint1) (nth 1 TrayFlangePoint1) (+ TrayDepth (nth 2 TrayFlangePoint1)))
				  TrayFlangePoint7 (polar TrayFlangePoint6 (+ TrayAngle (* PI  MB3DTF_FlipValue -0.5)) (* TrayFlange 0.5))
			)
			(command "3DPOLY" TrayBasePoint1 TrayFlangePoint1 TrayFlangePoint2 TrayFlangePoint3 TrayFlangePoint4 TrayFlangePoint5 TrayFlangePoint6 TrayFlangePoint7 "C")
		)
     )
     (command "Extrude" "l" "" "Dir" TrayBasePoint1 (polar TrayBasePoint1 Trayangle TrayLength))
     (setq TrayReturnEntity (entlast))
)

;;Work on Reverse Flange
(defun MEDBuild3DTrayFlange (MB3DTF_TrayData MB3DTF_FlipValue UCSData / TrayPoint1 TrayPoint2) ;Flip value is 1.0 normal opposite is -1
	;(princ "\nHere")
	(setq TrayPoint1 (nth 0 MB3DTF_TrayData)
		  TrayPoint2 (nth 1 MB3DTF_TrayData)
		  TrayWidth  (nth 2 MB3DTF_TrayData)
		  TrayDepth  (nth 3 MB3DTF_TrayData)
		  TrayFlange (MED3D-effFlange (nth 4 MB3DTF_TrayData))
		 ; UCSPoint1 (trans TrayPoint1 UCSData 0)
		 ; UCSPoint2 (trans TrayPoint2 UCSData 0)
		 ; UCSPoint3 (polar UCSPoint1 (+ (angle UCSPoint1 UCSPoint2) (* PI 0.5)) 1.0)
	)
	;(if (equal (dxf 210 TrayEntityData) (list 0.0 0.0 1.0))
	;	(command "UCS" "")
	;	(progn
	;		(command "UCS" "" "UCS" "n" "3p"  UCSPoint1 UCSPoint2 UCSPoint3)
	;		(setq TrayPoint1 (trans UCSPoint1 0 1)
	;			  TrayPoint2 (trans UCSPoint2 0 1)
	;		)
	;	)
	;)
	(setq TrayLength (distance TrayPoint1 TrayPoint2)
		  TrayAngle  (angle TrayPoint1 TrayPoint2)
		  TrayBasePoint1 (polar TrayPoint1 (+ TrayAngle (* MB3DTF_FlipValue PI 0.5)) (* TrayWidth 0.5))
	)
	(if (< (abs TrayFlange) (* 2.0 MED_TRAY_MATERIALWIDTH))
		(progn
			(setq TrayFlangePoint1 (polar TrayBasePoint1 (+ TrayAngle (*  MB3DTF_FlipValue PI 0.5)) MED_TRAY_MATERIALWIDTH)
				  TrayFlangePoint2 (list (nth 0 TrayFlangePoint1) (nth 1 TrayFlangePoint1) (+ TrayDepth (nth 2 TrayFlangePoint1)))
				  TrayFlangePoint3 (polar TrayFlangePoint2 (+ TrayAngle (* PI  MB3DTF_FlipValue -0.5)) MED_TRAY_MATERIALWIDTH)
			)
			(command "3DPOLY" TrayBasePoint1 TrayFlangePoint1 TrayFlangePoint2 TrayFlangePoint3 "C")
		)
		(progn
			(if (< TrayFlange 0.0)
				(setq FlangeFLIP T)
				(setq FlangeFLIP nil)
			)
				
			(setq TrayFlangePoint1 (polar TrayBasePoint1 (+ TrayAngle (*  MB3DTF_FlipValue PI 0.5)) (* TrayFlange 0.5))
				  TrayFlangePoint2 (list (nth 0 TrayFlangePoint1) (nth 1 TrayFlangePoint1) (+ MED_TRAY_MATERIALWIDTH (nth 2 TrayFlangePoint1)))
				  TrayFlangePoint3 (polar TrayFlangePoint2 (+ TrayAngle (* PI  MB3DTF_FlipValue -0.5)) (- (* TrayFlange 0.5) (if FlangeFlip (* -1 MED_TRAY_MATERIALWIDTH) MED_TRAY_MATERIALWIDTH)))
				  TrayFlangePoint4 (list (nth 0 TrayFlangePoint3) (nth 1 TrayFlangePoint3) (+ (- TrayDepth (* 2.0 MED_TRAY_MATERIALWIDTH)) (nth 2 TrayFlangePoint3)))
				  TrayFlangePoint5 (list (nth 0 TrayFlangePoint1) (nth 1 TrayFlangePoint1) (+ (- TrayDepth MED_TRAY_MATERIALWIDTH) (nth 2 TrayFlangePoint1)))
				  TrayFlangePoint6 (list (nth 0 TrayFlangePoint1) (nth 1 TrayFlangePoint1) (+ TrayDepth (nth 2 TrayFlangePoint1)))
				  TrayFlangePoint7 (polar TrayFlangePoint6 (+ TrayAngle (* PI  MB3DTF_FlipValue -0.5)) (* TrayFlange 0.5))
			)
			(command "3DPOLY" TrayBasePoint1 TrayFlangePoint1 TrayFlangePoint2 TrayFlangePoint3 TrayFlangePoint4 TrayFlangePoint5 TrayFlangePoint6 TrayFlangePoint7 "C")
		)
     )
     (command "Extrude" "l" "" "Dir" TrayBasePoint1 (polar TrayBasePoint1 Trayangle TrayLength))
     (setq TrayReturnEntity (entlast))
)


;This function simply needs same info as tray, but then pass it the offset entity form the MED Centerline Copy and it will create it nice and smooth
(defun MEDBuild3DTrayFitFlange (MB3DTF_TrayData MB3DTF_FlipValue MB3DTF_Entity NotVerticalTrayFlag / TrayPoint1 TrayPoint2 TrayAngle) ;Flip value is 1.0 normal opposite is -1
	(setq TrayPoint1 (nth 0 MB3DTF_TrayData)
		  TrayPoint2 (nth 1 MB3DTF_TrayData)
		  TrayWidth  (nth 2 MB3DTF_TrayData)
		  TrayDepth  (nth 3 MB3DTF_TrayData)
		  TrayFlange (MED3D-effFlange (nth 4 MB3DTF_TrayData))
		  TrayLength (distance TrayPoint1 TrayPoint2)
		  TrayAngle  (angle TrayPoint1 TrayPoint2)
		  TrayBasePoint1 (polar TrayPoint1 (+ TrayAngle (* MB3DTF_FlipValue PI 0.5)) (* TrayWidth 0.5))
	)
	(if (< TrayFlange (* 2.0 MED_TRAY_MATERIALWIDTH))
		(progn
			(setq TrayFlangePoint1 (polar TrayBasePoint1 (+ TrayAngle (*  MB3DTF_FlipValue PI 0.5)) MED_TRAY_MATERIALWIDTH)
				  TrayFlangePoint2 (list (nth 0 TrayFlangePoint1) (nth 1 TrayFlangePoint1) (+ TrayDepth (nth 2 TrayFlangePoint1)))
				  TrayFlangePoint3 (polar TrayFlangePoint2 (+ TrayAngle (* PI  MB3DTF_FlipValue -0.5)) MED_TRAY_MATERIALWIDTH)
			)
			(command "3DPOLY" TrayBasePoint1 TrayFlangePoint1 TrayFlangePoint2 TrayFlangePoint3 "C")
			(setq ExtrudeEntity (entlast))
		)
		(progn
			(setq TrayFlangePoint1 (polar TrayBasePoint1 (+ TrayAngle (*  MB3DTF_FlipValue PI 0.5)) (* TrayFlange 0.5))
				  TrayFlangePoint2 (list (nth 0 TrayFlangePoint1) (nth 1 TrayFlangePoint1) (+ MED_TRAY_MATERIALWIDTH (nth 2 TrayFlangePoint1)))
				  TrayFlangePoint3 (polar TrayFlangePoint2 (+ TrayAngle (* PI  MB3DTF_FlipValue -0.5)) (- (* TrayFlange 0.5) MED_TRAY_MATERIALWIDTH))
				  TrayFlangePoint4 (list (nth 0 TrayFlangePoint3) (nth 1 TrayFlangePoint3) (+ (- TrayDepth (* 2.0 MED_TRAY_MATERIALWIDTH)) (nth 2 TrayFlangePoint3)))
				  TrayFlangePoint5 (list (nth 0 TrayFlangePoint1) (nth 1 TrayFlangePoint1) (+ (- TrayDepth MED_TRAY_MATERIALWIDTH) (nth 2 TrayFlangePoint1)))
				  TrayFlangePoint6 (list (nth 0 TrayFlangePoint1) (nth 1 TrayFlangePoint1) (+ TrayDepth (nth 2 TrayFlangePoint1)))
				  TrayFlangePoint7 (polar TrayFlangePoint6 (+ TrayAngle (* PI  MB3DTF_FlipValue -0.5)) (* TrayFlange 0.5))
			)
			(command "3DPOLY" TrayBasePoint1 TrayFlangePoint1 TrayFlangePoint2 TrayFlangePoint3 TrayFlangePoint4 TrayFlangePoint5 TrayFlangePoint6 TrayFlangePoint7 "C")
			(setq ExtrudeEntity (entlast))
		)
			
     )
    (setq t1 VerticalTrayFlag)
     (if NotVerticalTrayFlag
     	 (command "offset" (distance TrayPoint1 TrayBasePoint1) MB3DTF_Entity TrayBasePoint1 "")
     	 (command "Copy" MB3DTF_Entity "" TrayPoint1 TrayBasePoint1)
     )
     (setq PathEntity (entlast))
     (command "Extrude" ExtrudeEntity "" "Path" Pathentity)
     (setq TrayReturnEntity (entlast))
)


;;Work on negative flange
(defun MEDBuild3DTrayFitFlange (MB3DTF_TrayData MB3DTF_FlipValue MB3DTF_Entity NotVerticalTrayFlag / TrayPoint1 TrayPoint2 TrayAngle) ;Flip value is 1.0 normal opposite is -1
	(setq TrayPoint1 (nth 0 MB3DTF_TrayData)
		  TrayPoint2 (nth 1 MB3DTF_TrayData)
		  TrayWidth  (nth 2 MB3DTF_TrayData)
		  TrayDepth  (nth 3 MB3DTF_TrayData)
		  TrayFlange (MED3D-effFlange (nth 4 MB3DTF_TrayData))
		  TrayLength (distance TrayPoint1 TrayPoint2)
		  TrayAngle  (angle TrayPoint1 TrayPoint2)
		  TrayBasePoint1 (polar TrayPoint1 (+ TrayAngle (* MB3DTF_FlipValue PI 0.5)) (* TrayWidth 0.5))
	)
	(if (< (abs TrayFlange) (* 2.0 MED_TRAY_MATERIALWIDTH))
		(progn
			(setq TrayFlangePoint1 (polar TrayBasePoint1 (+ TrayAngle (*  MB3DTF_FlipValue PI 0.5)) MED_TRAY_MATERIALWIDTH)
				  TrayFlangePoint2 (list (nth 0 TrayFlangePoint1) (nth 1 TrayFlangePoint1) (+ TrayDepth (nth 2 TrayFlangePoint1)))
				  TrayFlangePoint3 (polar TrayFlangePoint2 (+ TrayAngle (* PI  MB3DTF_FlipValue -0.5)) MED_TRAY_MATERIALWIDTH)
			)
			(command "3DPOLY" TrayBasePoint1 TrayFlangePoint1 TrayFlangePoint2 TrayFlangePoint3 "C")
			(setq ExtrudeEntity (entlast))
		)
		(progn
			(if (< TrayFlange 0.0)
				(setq FlangeFLIP T)
				(setq FlangeFLIP nil)
			)
			
			(setq TrayFlangePoint1 (polar TrayBasePoint1 (+ TrayAngle (*  MB3DTF_FlipValue PI 0.5)) (* TrayFlange 0.5))
				  TrayFlangePoint2 (list (nth 0 TrayFlangePoint1) (nth 1 TrayFlangePoint1) (+ MED_TRAY_MATERIALWIDTH (nth 2 TrayFlangePoint1)))
				  TrayFlangePoint3 (polar TrayFlangePoint2 (+ TrayAngle (* PI  MB3DTF_FlipValue -0.5)) (- (* TrayFlange 0.5) (if FlangeFlip (* -1 MED_TRAY_MATERIALWIDTH) MED_TRAY_MATERIALWIDTH)))
				  TrayFlangePoint4 (list (nth 0 TrayFlangePoint3) (nth 1 TrayFlangePoint3) (+ (- TrayDepth (* 2.0 MED_TRAY_MATERIALWIDTH)) (nth 2 TrayFlangePoint3)))
				  TrayFlangePoint5 (list (nth 0 TrayFlangePoint1) (nth 1 TrayFlangePoint1) (+ (- TrayDepth MED_TRAY_MATERIALWIDTH) (nth 2 TrayFlangePoint1)))
				  TrayFlangePoint6 (list (nth 0 TrayFlangePoint1) (nth 1 TrayFlangePoint1) (+ TrayDepth (nth 2 TrayFlangePoint1)))
				  TrayFlangePoint7 (polar TrayFlangePoint6 (+ TrayAngle (* PI  MB3DTF_FlipValue -0.5)) (* TrayFlange 0.5))
			)
			(command "3DPOLY" TrayBasePoint1 TrayFlangePoint1 TrayFlangePoint2 TrayFlangePoint3 TrayFlangePoint4 TrayFlangePoint5 TrayFlangePoint6 TrayFlangePoint7 "C")
			(setq ExtrudeEntity (entlast))
		)
			
     )
    (setq t1 VerticalTrayFlag)
     (if NotVerticalTrayFlag
     	 (command "offset" (distance TrayPoint1 TrayBasePoint1) MB3DTF_Entity TrayBasePoint1 "")
     	 (command "Copy" MB3DTF_Entity "" TrayPoint1 TrayBasePoint1)
     )
     (setq PathEntity (entlast))
     (command "Extrude" ExtrudeEntity "" "Path" Pathentity)
     (setq TrayReturnEntity (entlast))
)



;I used this to create a 90 degree Elbow travling up or at least the one line of it.
;(maketray (list (list (list 0.0 0.0) nil) (list (list 5.0 0.0) (* (* PI 0.5) 0.25)) (list (list 17.0 12.0) nil) (list (list 17.0 17.0) nil)) nil nil)

;Thsi one works to creat a 90 degree elbow down
;(maketray (list (list (list 0.0 0.0) nil) (list (list 5.0 0.0) (* -1.0 (* PI 0.5) 0.25)) (list (list 17.0 -12.0) nil) (list (list 17.0 -17.0) nil)) nil nil)
(defun c:QVTest()
	(setq _ZFLAG T)
	(setq t-pt1 (list 0.0 0.0)
		  t-pt2 (list 5.0 0.0)
		  t-pt3 (list 17.0 -12.0)
		  t-pt4 (list 17.0 -17.0)
		  t-list (list (list t-pt1 nil)
					   (list t-pt2 (* -1.0 (med_tan (* (* PI 0.5) 0.25))))
					   (list t-pt3 nil)
					   (list t-pt4 nil)
				 )
	)
	(maketray t-list nil nil)
)

(defun c:trayfittest()
	(MEDConvertTrayElbowto3d (car (entsel)))
)
(defun MEDConvertTrayElbowTo3D(TrayEntity / TrayEntityData TrayMEDData Tray3DEnt)
	(setq TrayEntityData (entget TrayEntity)
		  TrayMEDData (xdataget TrayEntity _FITTING)
	)
	(if (equal (dxf 210 TrayEntityData) (list 0.0 0.0 1.0))
		(command "UCS" "")
		(command "ucs" "OB" trayentity)
	)
	(MEDDraw3DTrayFit (list nil
			             	nil
			             (nth 2 TrayMEDData) ; Width
			             (nth 5 TrayMEDData) ; Depth
			             (MED3D-flangeFor TrayEntity _FITTING (nth 6 TrayMEDData)) ; FlangeSize
			       )
		           TrayEntity
	)
	;; MEDProperties FITTING (Length empty per schema)
	(setq Tray3DEnt (entlast))
	(MEDStamp3DFromBom Tray3DEnt TrayEntity "FITTING" nil)
	Tray3DEnt
)

(defun MEDDraw3DTrayFit (TrayDataList TrayCenterLine / TrayPoint1 TrayPoint2 TrayWidth TrayDepth TrayFlange) ; List includes StartPoint EndPoint Width Depth Flange
	(setq t1e Traycenterline)
	(setq t1d traydatalist)
	(setq Traypoints (bld_lw_ptlist TrayCenterLine)
		  TrayCenterLineData (entget TrayCenterLine)
		  TrayPoint38 (dxf 38 TrayCenterLineData)
	)
	(setq TrayPoint1 (trans (append (cdr (nth 0 (car TrayPoints))) (list traypoint38)) T1e 1) 
		  TrayPoint2 (trans (append (cdr (nth 1 (car TrayPoints))) (list traypoint38)) T1e 1)
	)
	(if (setq TrayfitVData (vtrayxdataget TrayCenterline))
		(progn
			;(sd)
			(command "UCS" "New" "3P" TrayPoint1 TrayPoint2 (list (car TrayPoint1) (cadr Traypoint1) (- (caddr TrayPoint1) 10.0)));(* 1.0 (nth 3 trayfitvdata)))))
			;(sd)
			(setq TrayPoint1 (trans (append (cdr (nth 0 (car TrayPoints))) (list traypoint38)) TrayCenterLine 1) 
		          TrayPoint2 (trans (append (cdr (nth 1 (car TrayPoints))) (list traypoint38)) TrayCenterLine 1)
		    )
		 )
	)
	(setq TrayWidth  (nth 2 TrayDataList)
		  TrayDepth  (nth 3 TrayDataList)
		  TrayFlange (nth 4 TrayDataList)
		  TrayDataList (list TrayPoint1 TrayPoint2 TrayWidth TrayDepth TrayFlange)
		  ;TrayAngle  (angle TrayPoint1 TrayPoint2)
		  TrayBaseEnt (MEDBuild3DTrayFitBase TrayDataList TrayCenterLine) 
		  TrayFlangeEnt1 (MEDBuild3DTrayFitFlange TrayDataList 1.0 TrayCenterLine (not (vtrayxdataget TrayCenterline)))
		  TrayFlangeEnt2 (MEDBuild3DTrayFitFlange TrayDataList -1.0 TrayCenterLine (not (vtrayxdataget TrayCenterline)))
		  ;TrayFlangeEnt1 (MEDBuild3DTrayFitFlange TrayDataList 1.0 TrayCenterLine (equal (dxf 210 TrayCenterLineData) (list 0.0 0.0 1.0)))
		  ;TrayFlangeEnt2 (MEDBuild3DTrayFitFlange TrayDataList -1.0 TrayCenterLine (equal (dxf 210 TrayCenterLineData) (list 0.0 0.0 1.0)))
    )
    (command "union" TrayBaseEnt TrayFlangeEnt1 TrayFlangeEnt2 "")
)    	  
(defun MEDBuild3DTrayFitBase (MB3DTB_TrayData MB3DTF_Entity / TrayPoint1 TrayPoint2 TrayAngle)
	(setq t1 MB3DTB_TrayData)
	(setq TrayPoint1 (nth 0 MB3DTB_TrayData)
		  TrayPoint2 (nth 1 MB3DTB_TrayData)
		  TrayWidth  (nth 2 MB3DTB_TrayData)
		  TrayAngle  (angle TrayPoint1 TrayPoint2)
		  TrayBasePoint1 (polar TrayPoint1 (+ TrayAngle (* PI 0.5)) (* TrayWidth 0.5))
		  TrayBasePoint2 (polar TrayPoint1 (+ TrayAngle (* PI -0.5)) (* TrayWidth 0.5))
		  TrayBasePoint3 (list (car TrayBasePoint2) (cadr TrayBasepoint2) (+ (caddr TrayBasePoint2) MED_TRAY_MATERIALWIDTH))
		  TrayBasePoint4 (list (car TrayBasePoint1) (cadr TrayBasepoint1) (+ (caddr TrayBasePoint1) MED_TRAY_MATERIALWIDTH))
     )
     (command "Copy" MB3DTF_Entity "" "0,0,0" "0,0,0")
     (setq PathEntity (entlast))
     (command "3DPOLY" TrayBasePoint1 TrayBasePoint2 TrayBasePoint3 TrayBasePoint4 "C")
     (command "Extrude" "l" "" "path" Pathentity)
     (setq TrayReturnEntity (entlast))
)

(defun MEDSet3DTrayLayer(trayentity / trayentityLayer traydesc trayLayer 3dtraylayername
                                         NewLayColor NewLayData col)
	;; Swivel centers sit on MED Center layer, not MED_TRAY-*, so the old
	;; substr->MEDTRAY* color lookup threw Automation Error. Key not found and
	;; aborted the whole MEDMAKE3D tray stage.
	;; swivel fix: resolve MEDTRAY* parent near the fitting (or fitting's own MEDTRAY* layer),
	;; then the normal MED_3DTRAY-{desc} path. Unresolved -> bare _MED3DTRAY (old). Never color-lookup MEDCENTER*.
	(setq trayentityLayer (dxf 8 (entget trayentity)))
	(if (and (boundp (quote MEDIsTraySwivelFit)) (MEDIsTraySwivelFit trayentity))
	  (if (not (wcmatch (strcase trayentityLayer) "MED_TRAY*,MEDTRAY*"))
	    (setq trayentityLayer
	      (if (boundp (quote medsw_parent_tray_layer))
	        (vl-catch-all-apply (function (lambda ( / p) (setq p (car (medsw_wpts trayentity))) (medsw_parent_tray_layer p))))
	        nil))))
	(if (or (null trayentityLayer) (vl-catch-all-error-p trayentityLayer)
	        (not (wcmatch (strcase trayentityLayer) "MED_TRAY*,MEDTRAY*")))
	  (if (and (boundp (quote _MED3DTRAY)) _MED3DTRAY) (progn (smlayer _MED3DTRAY) (princ)))
	  (progn
	    (setq traydesc (substr trayentityLayer 10)
	          trayLayer (strcat "MEDTRAY" traydesc)
	          3dtraylayername (strcat "MED_3DTRAY-" traydesc))
	    (if (not (tblsearch "layer" 3DTrayLayerName))
	      (progn
	        (setq col (vl-catch-all-apply (function MEDGetLayerColor) (list TrayLayer))
	              NewLayColor (cond
	                            ((vl-catch-all-error-p col) 2)
	                            ((not col) 2)
	                            (T col))
	              NewLayData (list 3dTrayLayerName NewLayColor "Continuous" nil))
	        (medsmlayer newlaydata))
	      (setvar "CLAYER" 3DtrayLayerName))))
)
	
	

;; 3DSOLIDs created after entity mark (all entities when mark is nil), still alive
(defun MEDNew3DSolidsAfter (mark / e out)
  (setq e (if mark (entnext mark) (entnext)))
  (while e
    (if (= (cdr (assoc 0 (entget e))) "3DSOLID") (setq out (cons e out)))
    (setq e (entnext e)))
  (reverse out))

;; Non-interactive tray worker shared by MAKE3DTRAY and MEDMAKE3D (MED3DPath.lsp).
;; Converts every MED_TRAY run and every MED_FITTING outline in the drawing with
;; the same per-entity code MAKE3DTRAY always used (layer, geometry unchanged),
;; then resets the UCS to World. No prompts, no sysvar handling (callers do that).
;; Returns (tray-solids fitting-solids skipped); skipped = ((handle kind reason) ...)
(defun med3d-tray-build ( / mark new traysols fitsols skipped)
	(MEDEnsureTraySwivelLoaded)
	(setq 3douttray (ssget "x" (list (list -3 (list "MED_TRAY")))))
	(if 3douttray
	  (progn
	    (setq trayoutnum (sslength 3douttray)
	   trayoutcnt 0
	    )
	    (while (< trayoutcnt trayoutnum)
	    	  (setq trayent (ssname 3douttray trayoutcnt)
	    	        mark    (entlast))
	    	  (MEDSet3DTrayLayer trayent)
	    	  (MEDConvertTrayto3d trayent)
	    	  (if (setq new (MEDNew3DSolidsAfter mark))
	    	    (setq traysols (append traysols new))
	    	    (setq skipped (cons (list (cdr (assoc 5 (entget trayent))) "TRAY" "no solid created") skipped)))
	    	  (setq trayoutcnt (1+ trayoutcnt))
	    )
	  )
	)
	(setq 3douttray (ssget "x" (list (list -3 (list "MED_FITTING")))))
	(if 3douttray
	   (progn
	     (setq trayoutnum (sslength 3douttray)
	     	   trayoutcnt 0
	     )
	     (while (< trayoutcnt trayoutnum)
	     	 (setq trayent (ssname 3douttray trayoutcnt)
	     	       mark    (entlast))
	     	 ;; block fittings (conduit bodies, couplings ...) are not tray outlines:
	     	 ;; MEDMAKE3D handles them in its conduit body stage (MED3DFittings.lsp)
	     	 (if (/= (cdr (assoc 0 (entget trayent))) "INSERT")
	     	   (progn
	     	     (MEDSet3DTrayLayer trayent)
	     	     (MEDConvertTrayFittingsTo3D trayent)
	     	     ;; 2026-10-29 swexport: collect 3DSOLID + INSERT so swivel plate blocks
	     	     ;; (3DTrayVerticalAdjSplice) reach the MEDMAKE3D export, same as Rungs.
	     	     (if (setq new (MEDNew3DEntsAfter mark))
	     	       (setq fitsols (append fitsols new))
	     	       (setq skipped (cons (list (cdr (assoc 5 (entget trayent))) "FITTING"
	     	                                 "no solid created (not an elbow / tee / cross / reducer outline)") skipped)))))
	     	 (setq trayoutcnt (1+ trayoutcnt))
	     )
	   )
	 )
	;; 2026-10-28 sbfix: COMMAND may not be apply-ed (vl-catch-all-apply 'command ...)
	;; -> "bad order function: COMMAND". Call it directly, as the Rungs path does.
	(if (> (getvar "CMDACTIVE") 0) (command))
	(command "_.UCS" "_W")
	(list traysols fitsols (reverse skipped))
)

(defun c:Make3DTray( / m3dOldOsmode m3dOldError )
	;; Running OSNAPS off for the whole export (restore on exit / error).
	(setq m3dOldOsmode (getvar "OSMODE")
	      m3dOldError *error*)
	(defun *error* ( msg )
	  (if m3dOldOsmode (setvar "OSMODE" m3dOldOsmode))
	  (setq *error* m3dOldError)
	  (if (and msg (/= msg "") (not (wcmatch (strcase msg t) "*break*,*cancel*,*exit*")))
	    (princ (strcat "\nMake3DTray: " msg))
	  )
	  (princ)
	)
	(setvar "OSMODE" 0)
	(smlayer _MED3DTRAY)
	(command "vpoint" "1,1,1")
	(initget "3DS Dwg Layer")
	(setq outputformat (getkword "\n Output to 3DS Layer <Dwg>: "))
	(if (not outputformat)
	  (setq outputformat "Dwg")
	)
	;; tray runs + tray fittings -> 3D (shared with MEDMAKE3D), UCS back to World
	(med3d-tray-build)
	(cond
    ((= outputformat "3DS")
      (Prompt "\nMake3dtray will export to 3ds file:")
      (if (not c:3dsout)
	(arxload "render")
      )
      (setq 3dsoutfname (getfiled "Select file name for 3Dtray output" (substr (getvar "dwgname") 1 (- (strlen (getvar "dwgname")) 4)) "3ds" 1))
      (c:3dsout (ssget "X" (list (cons 0 "3dsolid") (cons 8 (nth 0 _MED3DTRAY)))) 0 0 30 0.1 3dsoutfname)
      (command "erase" (ssget "X" (list (cons 0 "3dsolid") (cons 8 (nth 0 _MED3DTRAY)))) "")
      (command "plan" "")
      ;; 3DS export discards solids — no medprops.json
    )
    ;;testing default path as the drawing prefix
    ;(setq 3dsoutfname (getfiled "Select file name for 3Dtray output" (substr (getvar "dwgname") 1 (- (strlen (getvar "dwgname")) 4)) "dwg" 1))
    ((= outputformat "Dwg")
      (setq 3dsoutfname (if med3d-pick-writable-dwg (med3d-pick-writable-dwg "Select file name for 3Dtray output") (getfiled "Select file name for 3Dtray output" (getvar "dwgprefix") "dwg" 1)))   ; exlock 2026-10-29
      (if (not 3dsoutfname)
        (progn (command "erase" (ssget "X" (list (cons 0 "3dsolid") (cons 8 (nth 0 _MED3DTRAY)))) "") (command "plan" "") (princ "\nMake3dtray: export cancelled - 3D removed."))
      (progn
      (if (findfile 3dsoutfname)
	(command "wblock" 3dsoutfname "y" "")
	(command "wblock" 3dsoutfname "")
      )
      ;(command (list 0.0 0.0 0.0) (ssget "X" (list (cons 0 "3dsolid") (cons 8 (nth 0 _MED3DTRAY)))) "")
      (command (list 0.0 0.0 0.0) (ssget "X" (list (cons 0 "3dsolid") )) "")
      (command "plan" "")
      ;; Sidecar must sit beside the WBLOCK target (handles in that file), not the source DWG.
      (if (and 3dsoutfname (findfile 3dsoutfname))
        (MEDRebuildMedPropsJsonBeside 3dsoutfname)
      )
      ))   ; exlock 2026-10-29
    )
    ((= outputformat "Layer")
      ;(command "-layer" "off" "*" "" "On" (nth 0 _MED3DTRAY) "")
      (prompt "\nUse the PLAN command to return to plan view:")
      ;; Solids remain in the active drawing — rebuild sibling JSON if DWG is saved.
      (MEDRebuildMedPropsJsonBeside nil)
    )
  )

	(setvar "OSMODE" m3dOldOsmode)
	(setq *error* m3dOldError)
	(princ)

)

;; Tray swivel = ITEMCODE 390 (*MEDSW-FITCODE*). Check CODE before any geometry
;; (2-pt centers otherwise fall into LR-reducer extrude and bomb).
(defun MEDIsTraySwivelFit (ent / xd code) ; swxdata2 2026-10-29: 367 (390 is a real VINELBOW)
  (setq xd (xdataget ent _FITTING)
        code (if xd (nth 3 xd) nil))
  (and code
       (= code (if (boundp (quote *MEDSW-FITCODE*)) *MEDSW-FITCODE* 367)))
)

(defun MEDEnsureTraySwivelLoaded ( / )
  (if (not (boundp (quote MEDConvertTraySwivelTo3D)))
    (vl-catch-all-apply (function load) (list "MEDTraySwivel")))
  (boundp (quote MEDConvertTraySwivelTo3D))
)

(defun MEDConvertTrayFittingsTo3D (trayfitent)
  (setq fitptbllist (bld_lw_ptlist trayfitent)
  	    fitptlist   (nth 0 fitptbllist)
  	    fitbllist   (nth 1 fitptbllist)
  	    Trayfitdata (xdataget trayfitent _FITTING)
  	    fitwidth    (nth 2 trayfitdata)
  	    fitdpth     (nth 5 trayfitdata)
  	    fitalt      (nth 4 trayfitdata)
  	    m3delev     (getvar "ELEVATION")
  	    trayfitentdata (entget trayfitent)
  )
  (setvar "ELEVATION" (dxf 38 trayfitentdata))
  
  (cond
    ;; FIRST: swivel by ITEMCODE — never send these to elbow/reducer extrude
    ((MEDIsTraySwivelFit trayfitent)
       (if (MEDEnsureTraySwivelLoaded)
         (MEDConvertTraySwivelTo3D trayfitent)
         (princ "\n  Swivel fitting: load MEDTraySwivel.lsp (Support path)."))
    )
    ((= (length fitptlist) 4)
    		(MEDConvertTrayElbowTo3D trayfitent)
    )
    ((= (length fitptlist) 7)
    		(MEDConvertTrayTeeTo3D trayfitent)
    )
    ((= (length fitptlist) 10)
    	  	(MEDConvertTrayTeeTo3D trayfitent)
    )
    ((and (= (length fitptlist) 2)
	  (= 18.0 (distance (cdr (nth 0 fitptlist)) (cdr (nth 1 fitptlist)))))
       (MEDConvertTrayReducerTo3d trayfitent)
    )
    ((and (= (length fitptlist) 2)
          (> (rem (distance (cdr (nth 0 fitptlist)) (cdr (nth 1 fitptlist))) 1.0) 0.0))
       (MEDConvertTrayLRReducerTo3d trayfitent)
     )
    (T nil)
    
  )
  (setvar "ELEVATION" m3delev)
  
)

(defun MEDCopyEntity(EntityToCopy / CopyEntityData)
	(setq CopyEntityData (entget EntityToCopy)
		  CopyEntityData (cdr CopyEntityData)
	      CopyEntityData (entmake CopyEntityData)
	)
	(if CopyentityData
		(setq ReturnEntity (entlast))
		(setq ReturnEntity nil)
	)
	ReturnEntity
)


(defun MEDDraw3DTrayTeeCrossFit (TrayDataList TrayCenterLine /
		  TrayPoint1 TrayPoint2 TrayPoint3 TrayPoint4 TrayPoint5 TrayPoint6 TrayPoint7 TrayWidth TrayDepth TrayFlange) ; List includes StartPoint EndPoint Width Depth Flange
	(setq Traypoints (bld_lw_ptlist TrayCenterLine)
		  TrayCenterLineData (entget TrayCenterLine)
		  TrayPoint38 (dxf 38 TrayCenterLineData)
		  TrayPoint1 (trans (append (cdr (nth 0 (car TrayPoints))) (list traypoint38)) TrayCenterLine 1) 
		  TrayPoint2 (trans (append (cdr (nth 1 (car TrayPoints))) (list traypoint38)) TrayCenterLine 1)
		  TrayPoint3 (trans (append (cdr (nth 2 (car TrayPoints))) (list traypoint38)) TrayCenterLine 1)
		  TrayPoint4 (trans (append (cdr (nth 3 (car TrayPoints))) (list traypoint38)) TrayCenterLine 1)
		  TrayPoint5 (trans (append (cdr (nth 4 (car TrayPoints))) (list traypoint38)) TrayCenterLine 1)
		  TrayPoint6 (trans (append (cdr (nth 5 (car TrayPoints))) (list traypoint38)) TrayCenterLine 1)
		  TrayPoint7 (trans (append (cdr (nth 6 (car TrayPoints))) (list traypoint38)) TrayCenterLine 1)
		  TrayWidth  (nth 2 TrayDataList)
		  TrayDepth  (nth 3 TrayDataList)
		  TrayFlange (nth 4 TrayDataList)
		  TrayDataList (list TrayPoint1 TrayPoint2 TrayWidth TrayDepth TrayFlange)
		  ;TrayAngle  (angle TrayPoint1 TrayPoint2)
		  TrayBaseEnt (MEDBuild3DTrayBaseFromOutline TrayCenterLine)
		  TrayElevation (setvar "ELEVATION" TrayPoint38)
		  TempTrayCenter (MEDmaketray (list (list TrayPoint1 nil) (list TrayPoint2 (cdr (nth 1 (cadr Traypoints)))) (list TrayPoint3 nil) (list TrayPoint4 nil)) nil nil (MEDGetCurrentOCS))
		  TempTrayCenter (entlast)
		  TrayFlangeEnt1 (MEDBuild3DTrayFitFlange TrayDataList 1.0 TempTrayCenter (not (vtrayxdataget TrayCenterline)))
		  TempTrayCenter (entdel TempTrayCenter)
		  TrayDataList (list TrayPoint4 TrayPoint5 TrayWidth TrayDepth TrayFlange)
		  TrayElevation (setvar "ELEVATION" TrayPoint38)
		  TempTrayCenter (MEDmaketray (list (list TrayPoint4 nil) (list TrayPoint5 (cdr (nth 4 (cadr Traypoints)))) (list TrayPoint6 nil) (list TrayPoint7 nil)) nil nil (MEDGetCurrentOCS))
		  TempTrayCenter (entlast)
		  TrayFlangeEnt2 (MEDBuild3DTrayFitFlange TrayDataList 1.0 TempTrayCenter (not (vtrayxdataget TrayCenterline)))
		  TempTrayCenter (entdel TempTrayCenter)
    )
    (if (= (length (car TrayPoints)) 7)
    	(progn
    		(setq TrayDataList (list TrayPoint7 TrayPoint1 TrayWidth TrayDepth TrayFlange)
    			  TrayFlangeEnt3 (MEDBuild3DTrayFlange TrayDataList 1.0 (dxf 210 TRayCenterLineData))
    		)
    		(command "union" TrayBaseEnt TrayFlangeEnt1 TrayFlangeEnt2 TrayFlangeEnt3 "")
    	)
    	(progn
    		(setq TrayPoint8 (trans (append (cdr (nth 7 (car TrayPoints))) (list traypoint38)) TrayCenterLine 1)
    			  TrayPoint9 (trans (append (cdr (nth 8 (car TrayPoints))) (list traypoint38)) TrayCenterLine 1)
    			  TrayPoint10 (trans (append (cdr (nth 9 (car TrayPoints))) (list traypoint38)) TrayCenterLine 1)
    			  TrayDataList (list TrayPoint7 TrayPoint8 TrayWidth TrayDepth TrayFlange)
    			  TrayElevation (setvar "ELEVATION" TrayPoint38)
    			  TempTrayCenter (maketray (list (list TrayPoint7 nil) (list TrayPoint8 (cdr (nth 4 (cadr Traypoints)))) (list TrayPoint9 nil) (list TrayPoint10 nil)) nil nil)
    			  TempTrayCenter (entlast)
    			  TrayFlangeEnt3 (MEDBuild3DTrayFitFlange TrayDataList 1.0 TempTrayCenter (not (vtrayxdataget TrayCenterline)))
    			  TempTrayCenter (entdel TempTrayCenter)
    			  TrayDataList (list TrayPoint10 TrayPoint9 TrayWidth TrayDepth TrayFlange)
    			  TrayElevation (setvar "ELEVATION" TrayPoint38)
    			  TempTrayCenter (maketray (list (list TrayPoint10 nil) (list TrayPoint9 (cdr (nth 1 (cadr Traypoints)))) (list TrayPoint2 nil) (list TrayPoint1 nil)) nil nil)
    			  TempTrayCenter (entlast)
    			  TrayFlangeEnt4 (MEDBuild3DTrayFitFlange TrayDataList 1.0 TempTrayCenter (not (vtrayxdataget TrayCenterline)))
    			  TempTrayCenter (entdel TempTrayCenter)
    		)
    		(command "union" TrayBaseEnt TrayFlangeEnt1 TrayFlangeEnt2 TrayFlangeEnt3 TrayFlangeEnt4 "")
    	)
    		
    )
)    	 
    
(defun MEDBuild3DTrayBaseFromOutline (TrayCenterline)
	(setq TrayFittingData (xdataget TrayCenterLine _FITTING))
	(mtrayfit TrayCenterLine TrayFittingData T)
	(setq TrayFittingOutlineEnt (entlast))
	(command "Extrude" "l" "" MED_TRAY_MATERIALWIDTH)
    (setq TrayReturnEntity (entlast))
)

(defun c:trayteetest()
	(MEDConvertTrayTeeTo3d (car (entsel)))
)
(defun MEDConvertTrayTeeTo3D(TrayEntity / TrayEntityData TrayMEDData Tray3DEnt)
	(setq TrayEntityData (entget TrayEntity)
		  TrayMEDData (xdataget TrayEntity _FITTING)
	)
	(if (equal (dxf 210 TrayEntityData) (list 0.0 0.0 1.0))
		(command "UCS" "")
		(command "ucs" "OB" trayentity)
	)
	(MEDDraw3DTrayTeeCrossFit (list nil
			             nil
			             (nth 2 TrayMEDData) ; Width
			             (nth 5 TrayMEDData) ; Depth
			             (MED3D-flangeFor TrayEntity _FITTING (nth 6 TrayMEDData)) ; FlangeSize
			       )
		           TrayEntity
	)
	;; MEDProperties FITTING (Length empty per schema)
	(setq Tray3DEnt (entlast))
	(MEDStamp3DFromBom Tray3DEnt TrayEntity "FITTING" nil)
	Tray3DEnt
)

(defun MEDBuild3DTrayFlangeFromEntity (MB3DTF_TrayData MB3DTF_FlipValue MB3DTF_Entity / TrayPoint1 TrayPoint2 TrayAngle) ;Flip value is 1.0 normal opposite is -1
	(setq TrayPoint1 (nth 0 MB3DTF_TrayData)
		  TrayPoint2 (nth 1 MB3DTF_TrayData)
		  TrayWidth  (nth 2 MB3DTF_TrayData)
		  TrayDepth  (nth 3 MB3DTF_TrayData)
		  TrayFlange (MED3D-effFlange (nth 4 MB3DTF_TrayData))
		  TrayLength (distance TrayPoint1 TrayPoint2)
		  TrayAngle  (angle TrayPoint1 TrayPoint2)
		  TrayBasePoint1 (polar TrayPoint1 (+ TrayAngle (* MB3DTF_FlipValue PI 0.5)) (* TrayWidth 0.5))
;		  TrayFlangePoint1 (polar TrayBasePoint1 (+ TrayAngle (*  MB3DTF_FlipValue PI 0.5)) (* TrayFlange 0.5))
;		  TrayFlangePoint2 (list (nth 0 TrayFlangePoint1) (nth 1 TrayFlangePoint1) (+ MED_TRAY_MATERIALWIDTH (nth 2 TrayFlangePoint1)))
;		  TrayFlangePoint3 (polar TrayFlangePoint2 (+ TrayAngle (* PI  MB3DTF_FlipValue -0.5)) (- (* TrayFlange 0.5) MED_TRAY_MATERIALWIDTH))
;		  TrayFlangePoint4 (list (nth 0 TrayFlangePoint3) (nth 1 TrayFlangePoint3) (+ (- TrayDepth (* 2.0 MED_TRAY_MATERIALWIDTH)) (nth 2 TrayFlangePoint3)))
;		  TrayFlangePoint5 (list (nth 0 TrayFlangePoint1) (nth 1 TrayFlangePoint1) (+ (- TrayDepth MED_TRAY_MATERIALWIDTH) (nth 2 TrayFlangePoint1)))
;		  TrayFlangePoint6 (list (nth 0 TrayFlangePoint1) (nth 1 TrayFlangePoint1) (+ TrayDepth (nth 2 TrayFlangePoint1)))
;		  TrayFlangePoint7 (polar TrayFlangePoint6 (+ TrayAngle (* PI  MB3DTF_FlipValue -0.5)) (* TrayFlange 0.5))
;     )
;     (command "3DPOLY" TrayBasePoint1 TrayFlangePoint1 TrayFlangePoint2 TrayFlangePoint3 TrayFlangePoint4 TrayFlangePoint5 TrayFlangePoint6 TrayFlangePoint7 "C")
;     (command "Extrude" "l" "" "Path" MB3DTF_Entity)
;     (setq TrayReturnEntity (entlast))
	)
	(if (< (abs TrayFlange) (* 2.0 MED_TRAY_MATERIALWIDTH))
		(progn
			(setq TrayFlangePoint1 (polar TrayBasePoint1 (+ TrayAngle (*  MB3DTF_FlipValue PI 0.5)) MED_TRAY_MATERIALWIDTH)
				  TrayFlangePoint2 (list (nth 0 TrayFlangePoint1) (nth 1 TrayFlangePoint1) (+ TrayDepth (nth 2 TrayFlangePoint1)))
				  TrayFlangePoint3 (polar TrayFlangePoint2 (+ TrayAngle (* PI  MB3DTF_FlipValue -0.5)) MED_TRAY_MATERIALWIDTH)
			)
			(command "3DPOLY" TrayBasePoint1 TrayFlangePoint1 TrayFlangePoint2 TrayFlangePoint3 "C")
		)
		(progn
			(if (< TrayFlange 0.0)
				(setq FlangeFLIP T)
				(setq FlangeFLIP nil)
			)
			(setq t1 MB3Dtf_TrayData t2 Traybasepoint1 t3 Traybasepoint2)
			(setq TrayFlangePoint1 (polar TrayBasePoint1 (+ TrayAngle (*  MB3DTF_FlipValue PI 0.5)) (* TrayFlange 0.5))
				  TrayFlangePoint2 (list (nth 0 TrayFlangePoint1) (nth 1 TrayFlangePoint1) (+ MED_TRAY_MATERIALWIDTH (nth 2 TrayFlangePoint1)))
				  TrayFlangePoint3 (polar TrayFlangePoint2 (+ TrayAngle (* PI  MB3DTF_FlipValue -0.5)) (- (* TrayFlange 0.5) (if FlangeFlip (* -1 MED_TRAY_MATERIALWIDTH) MED_TRAY_MATERIALWIDTH)))
				  TrayFlangePoint4 (list (nth 0 TrayFlangePoint3) (nth 1 TrayFlangePoint3) (+ (- TrayDepth (* 2.0 MED_TRAY_MATERIALWIDTH)) (nth 2 TrayFlangePoint3)))
				  TrayFlangePoint5 (list (nth 0 TrayFlangePoint1) (nth 1 TrayFlangePoint1) (+ (- TrayDepth MED_TRAY_MATERIALWIDTH) (nth 2 TrayFlangePoint1)))
				  TrayFlangePoint6 (list (nth 0 TrayFlangePoint1) (nth 1 TrayFlangePoint1) (+ TrayDepth (nth 2 TrayFlangePoint1)))
				  TrayFlangePoint7 (polar TrayFlangePoint6 (+ TrayAngle (* PI  MB3DTF_FlipValue -0.5)) (* TrayFlange 0.5))
			)
			(command "3DPOLY" TrayBasePoint1 TrayFlangePoint1 TrayFlangePoint2 TrayFlangePoint3 TrayFlangePoint4 TrayFlangePoint5 TrayFlangePoint6 TrayFlangePoint7 "C")
		)
     )
     ;(command "Extrude" "l" "" "Dir" TrayBasePoint1 (polar TrayBasePoint1 Trayangle TrayLength))
     (command "Extrude" "l" "" "Path" MB3DTF_Entity)
     (setq TrayReturnEntity (entlast))
)

(defun MEDDraw3DTrayStraightReducer (TrayDataList TrayCenterLine /
		  TrayPoint1 TrayPoint2 TrayPoint3 TrayPoint4 TrayWidth TrayDepth TrayFlange TrayAngle) ; List includes StartPoint EndPoint Width Depth Flange
	(setq Traypoints (bld_lw_ptlist TrayCenterLine)
		  TrayReducerData (entget TrayCenterLine)
		  TrayPoint38 (dxf 38 TrayReducerData)
		  TrayPoint1 (trans (append (cdr (nth 0 (car TrayPoints))) (list traypoint38)) TrayCenterLine 1)
		  t1 TrayPoint1
		  TrayPoint2 (trans (append (cdr (nth 1 (car TrayPoints))) (list traypoint38)) TrayCenterLine 1)
		  t2 TrayPoint2
		  t3 Trayreducerdata
		  TrayWidth  (nth 2 TrayDataList)
		  TrayDepth  (nth 3 TrayDataList)
		  TrayFlange (nth 4 TrayDataList)
		  TrayAltWidth (nth 4 (xdataget TrayCenterLine _FITTING))
		  TrayAngle  (angle TrayPoint1 TrayPoint2)
		  tandist 7.0
	      apt1 (polar TrayPoint1 (- TrayAngle (* PI 0.5)) (* 0.5 (* _PLOTSCALE TrayWidth)))
	      apt2 (polar TrayPoint1 (+ TrayAngle (* PI 0.5)) (* 0.5 (* _PLOTSCALE TrayWidth))) ; was TrayPoint2: rail path doubled back, EXTRUDE failed
	      apt3 (polar apt1 TrayAngle (* _PLOTSCALE tandist))
	      apt4 (polar apt2 TrayAngle (* _PLOTSCALE tandist))
	      bpt1 (polar TrayPoint2 (+ TrayAngle (* PI 0.5)) (* 0.5 (* _PLOTSCALE TrayAltWidth)))
	      bpt2 (polar TrayPoint2 (- TrayAngle (* PI 0.5)) (* 0.5 (* _PLOTSCALE TrayAltWidth)))
	      bpt3 (polar bpt1 (+ PI TrayAngle) (* _PLOTSCALE tandist))
	      bpt4 (polar bpt2 (+ PI TrayAngle) (* _PLOTSCALE tandist))
		  TrayDataList (list TrayPoint1 TrayPoint2 TrayWidth TrayDepth TrayFlange)
		  TrayBaseEnt (MEDBuild3DTrayBaseFromOutline TrayCenterLine)
		  mlist (list (list apt2 nil) (list apt4 nil) (list bpt3 nil) (list bpt1 nil))   
		  TempTrayCenter (MEDmaketray mlist nil nil (MEDGetCurrentOCS))
		  TempTrayCenter (entlast)
		  TrayFlangeEnt1 (MEDBuild3DTrayFlangeFromEntity TrayDataList 1.0 TempTrayCenter)
		  TempTrayCenter (if (entget TempTrayCenter) (entdel TempTrayCenter))
		  mlist (list (list apt1 nil) (list apt3 nil) (list bpt4 nil) (list bpt2 nil))   
		  TempTrayCenter (MEDmaketray mlist nil nil (MEDGetCurrentOCS))
		  TempTrayCenter (entlast)
		  TrayFlangeEnt2 (MEDBuild3DTrayFlangeFromEntity TrayDataList -1.0 TempTrayCenter)
		  TempTrayCenter (if (entget TempTrayCenter) (entdel TempTrayCenter))
    )
    (command "union" TrayBaseEnt TrayFlangeEnt1 TrayFlangeEnt2 "")
)

(defun MEDDraw3DTrayLeftOrRightReducer (TrayDataList TrayCenterLine /
		  TrayPoint1 TrayPoint2 TrayPoint3 TrayPoint4 TrayWidth TrayDepth TrayFlange TrayAngle) ; List includes StartPoint EndPoint Width Depth Flange
	(setq Traypoints (bld_lw_ptlist TrayCenterLine)
		  TrayReducerData (entget TrayCenterLine)
		  TrayPoint38 (dxf 38 TrayReducerData)
		  TrayPoint1 (trans (append (cdr (nth 0 (car TrayPoints))) (list traypoint38)) TrayCenterLine 1)
		  TrayPoint2 (trans (append (cdr (nth 1 (car TrayPoints))) (list traypoint38)) TrayCenterLine 1)
		  t1 TrayPoint1
		  t2 TrayPoint2
		  TrayWidth  (nth 2 TrayDataList)
		  TrayDepth  (nth 3 TrayDataList)
		  TrayFlange (nth 4 TrayDataList)
		  TrayReducerData (xdataget TrayCenterLine _FITTING)
		  TrayAltWidth (nth 4 TrayReducerData)
		  ReducerData (med_getdesc "FITTING" (nth 3 TrayReducerData)) 
	)
	(if (= (strcase (substr ReducerData 1 1)) "L")
		(setq DirectionFactor 1)
		(setq DirectionFactor -1)
	)
	(setq TrueAngle  (angle TrayPoint2 TrayPoint1)
		  tandist 7.0
		  ReducerLength (distance TrayPoint1 TrayPoint2)
		  StockReducerLength 18.0
		  HalfAlt (* (- TrayWidth TrayAltWidth 0.5))
		  HalfSize2 (* TrayAltWidth 0.5)
		  SinOfAngle (/ ReducerLength StockReducerLength)
		  CosOfAngle (/ halfAlt StockReducerLength)
		  AngleOfFittingLine (* DirectionFactor (atan (/ SinOfAngle CosOfAngle)))
		  TrayAngle (+ TrueAngle AngleOfFittingLine)
		  OtherPoint2 (polar TrayPoint2 TrayAngle HalfAlt)
		  Trayangle (angle TrayPoint1 OtherPoint2)
		  OtherPoint2 (polar TrayPoint1 TrayAngle StockReducerLength)
	      apt1 (polar TrayPoint2 (+ TrayAngle (* DirectionFactor (* PI 0.5))) (* _PLOTSCALE HalfSize2))
	      apt2 (polar apt1 (+ TrayAngle PI) (* StockReducerLength _PLOTSCALE)) 
	      apt3 (polar  apt2 (- Trayangle (* DirectionFactor (* PI 0.5))) (* TrayWidth _PLOTSCALE))
	      t37 TrayAngle
	      apt4 (polar apt3 TrayAngle (* tandist _PLOTSCALE))
	      apt6 (polar TrayPoint2 (+ TrayAngle (* DirectionFactor (* PI 1.5))) (* _PLOTSCALE HalfSize2))
	      apt5 (polar apt6 (+ TrayAngle PI) (* tandist _PLOTSCALE))
		  TrayDataList (list TrayPoint1 TrayPoint2 TrayWidth TrayDepth TrayFlange)
		  TrayBaseEnt (MEDBuild3DTrayBaseFromOutline TrayCenterLine)
		  UseThisAngle (angle apt3 apt4)
		  OtherPoint2 (polar TrayPoint1 UseThisAngle StockReducerLength)
		  mlist (list (list apt2 nil) (list apt1 nil))   
		  TempTrayCenter (MEDmaketray mlist nil nil (MEDGetCurrentOCS))
		  TempTrayCenter (entlast)
		  TrayDataList (list TrayPoint1 OtherPoint2 TrayWidth TrayDepth TrayFlange)
		  TrayFlangeEnt1 (MEDBuild3DTrayFlangeFromEntity TrayDataList (* 1.0 DirectionFactor) TempTrayCenter)
		  TempTrayCenter (if (entget TempTrayCenter) (entdel TempTrayCenter))
		  t5 Trayangle
		  mlist (list (list apt3 nil) (list apt4 nil) (list apt5 nil) (list apt6 nil))   
		  TempTrayCenter (MEDmaketray mlist nil nil (MEDGetCurrentOCS))
		  TempTrayCenter (entlast)
		  TrayFlangeEnt2 (MEDBuild3DTrayFlangeFromEntity TrayDataList (* -1.0 DirectionFactor) TempTrayCenter)
		  TempTrayCenter (if (entget TempTrayCenter) (entdel TempTrayCenter))
    )
    (command "union" TrayBaseEnt TrayFlangeEnt1 TrayFlangeEnt2 "")
)   


(defun c:trayretest()
	(MEDConvertTrayReducerTo3d (car (entsel)))
)
(defun MEDConvertTrayReducerTo3D(TrayEntity / TrayEntityData TrayMEDData Tray3DEnt)
	(setq TrayEntityData (entget TrayEntity)
		  TrayMEDData (xdataget TrayEntity _FITTING)
	)
	(if (equal (dxf 210 TrayEntityData) (list 0.0 0.0 1.0))
		(command "UCS" "")
		(command "ucs" "OB" trayentity)
	)
	(MEDDraw3DTrayStraightReducer (list nil
			             nil
			             (nth 2 TrayMEDData) ; Width
			             (nth 5 TrayMEDData) ; Depth
			             (MED3D-flangeFor TrayEntity _FITTING (nth 6 TrayMEDData)) ; FlangeSize
			       )
		           TrayEntity
	)
	;; MEDProperties FITTING (Length empty per schema)
	(setq Tray3DEnt (entlast))
	(MEDStamp3DFromBom Tray3DEnt TrayEntity "FITTING" nil)
	Tray3DEnt
)
      	  
	
(defun c:traylrretest()
	(MEDConvertTrayLRReducerTo3d (car (entsel)))
)
(defun MEDConvertTrayLRReducerTo3D(TrayEntity / TrayEntityData TrayMEDData Tray3DEnt)
	(setq TrayEntityData (entget TrayEntity)
		  TrayMEDData (xdataget TrayEntity _FITTING)
	)
	(if (equal (dxf 210 TrayEntityData) (list 0.0 0.0 1.0))
		(command "UCS" "")
		(command "ucs" "OB" trayentity)
	)
	(MEDDraw3DTrayLeftOrRightReducer (list nil
			             nil
			             (nth 2 TrayMEDData) ; Width
			             (nth 5 TrayMEDData) ; Depth
			             (MED3D-flangeFor TrayEntity _FITTING (nth 6 TrayMEDData)) ; FlangeSize
			       )
		           TrayEntity
	)
	;; MEDProperties FITTING (Length empty per schema)
	(setq Tray3DEnt (entlast))
	(MEDStamp3DFromBom Tray3DEnt TrayEntity "FITTING" nil)
	Tray3DEnt
)
      	  
;; !! 2026-10-28 GUARD (t848u): this file carries the Solid/Rungs toggle
;; !! (med3d-tray-build-style / med3d-ladder-build). When shipping MEDTraySwivel,
;; !! do NOT replace this file or MED3DLadderTray.lsp from a pre-rungs / pre-UCS
;; !! snapshot. Ship only these two live Support files or MERGE. MD5s: Jane/Bean/MED3D-CHECK.txt
;; !! MEDTraySwivel.lsp is also soft-loaded below (not a reason to replace this file from a swivel-only ship).
;; Open-bottom ladder tray (Make3DLadderTray) - separate file, soft-load.
;; Kept out of MEDCore; loads whenever MED3DTrayFunctions loads (Support path).
(if (findfile "MED3DLadderTray.lsp")
  (if (vl-catch-all-error-p (vl-catch-all-apply (quote load) (list "MED3DLadderTray.lsp")))
    (princ "\nMED3DLadderTray.lsp failed to load; APPLOAD it to see the error."))
  (princ "\nMED3DLadderTray.lsp not on support path."))
;; Tray swivel (TRAYSWIVEL + MEDConvertTraySwivelTo3D) - soft-load with tray functions.
(if (findfile "MEDTraySwivel.lsp")
  (if (vl-catch-all-error-p (vl-catch-all-apply (quote load) (list "MEDTraySwivel.lsp")))
    (princ "\nMEDTraySwivel.lsp failed to load; APPLOAD it to see the error."))
  (princ "\nMEDTraySwivel.lsp not on support path."))
;; ---- MEDMAKE3D tray style (MED Properties > Tray: Tray Bottom / Tray Segment Length)
;; _TRAY3DBOTTOM "SOLID" (default) | "RUNGS";  _TRAYSEGLEN real, default 240.0
(defun med3d-tray-rungs-p ()
  (and (= (type _TRAY3DBOTTOM) 'STR) (wcmatch (strcase _TRAY3DBOTTOM) "RUNG*")))
(defun med3d-tray-seglen ()
  (cond ((and (numberp _TRAYSEGLEN) (> _TRAYSEGLEN 0.0)) (float _TRAYSEGLEN))
        ((and (numberp MED_TRAY_SEGLEN) (> MED_TRAY_SEGLEN 0.0)) (float MED_TRAY_SEGLEN))
        (T 240.0)))
(defun MEDNew3DEntsAfter (mark / e out typ)
  (setq e (if mark (entnext mark) (entnext)))
  (while e
    (setq typ (cdr (assoc 0 (entget e))))
    (if (member typ (list "3DSOLID" "INSERT")) (setq out (cons e out)))
    (setq e (entnext e)))
  (reverse out))
;; Ladder (rung) worker for MEDMAKE3D: same return shape as med3d-tray-build
;; (tray-ents fitting-ents skipped). Pieces are block INSERTs (MED3DLadderTray.lsp).
(defun med3d-ladder-build ( / ss i ent mark new traysols fitsols skipped seglen basemat oldatt oldexp olddel oldelev)
  (if (not MED3DL-doTray)
    (vl-catch-all-apply 'load (list "MED3DLadderTray.lsp")))
  (if (not MED3DL-doTray)
    (progn (princ "\nMEDMAKE3D: MED3DLadderTray.lsp not loaded - using solid bottom tray.")
           (med3d-tray-build))
    (progn
      (setq seglen (med3d-tray-seglen)
            MED_TRAY_SEGLEN seglen
            basemat MED_TRAY_MATERIALWIDTH
            oldatt (getvar "ATTREQ") oldexp (getvar "EXPERT") olddel (getvar "DELOBJ") oldelev (getvar "ELEVATION"))
      (setvar "ATTREQ" 0) (setvar "EXPERT" 5) (setvar "DELOBJ" 1)
      (if (setq ss (ssget "_X" (list (list -3 (list "MED_TRAY")))))
        (progn (setq i 0)
          (while (< i (sslength ss))
            (setq ent (ssname ss i) mark (entlast))
            (vl-catch-all-apply 'MED3DL-doTray (list ent seglen))
            (if (setq new (MEDNew3DEntsAfter mark))
              (setq traysols (append traysols new))
              (setq skipped (cons (list (cdr (assoc 5 (entget ent))) "TRAY" "no ladder piece created") skipped)))
            (setq i (1+ i)))))
      (if (setq ss (ssget "_X" (list (list -3 (list "MED_FITTING")))))
        (progn (setq i 0)
          (while (< i (sslength ss))
            (setq ent (ssname ss i) mark (entlast))
            (if (/= (cdr (assoc 0 (entget ent))) "INSERT")
              (progn
                (vl-catch-all-apply 'MED3DL-doFitting (list ent))
                (if (setq new (MEDNew3DEntsAfter mark))
                  (setq fitsols (append fitsols new))
                  (setq skipped (cons (list (cdr (assoc 5 (entget ent))) "FITTING"
                                            "no ladder fitting created") skipped)))))
            (setq i (1+ i)))))
      (if basemat (setq MED_TRAY_MATERIALWIDTH basemat))
      (setvar "ATTREQ" oldatt) (setvar "EXPERT" oldexp) (setvar "DELOBJ" olddel) (setvar "ELEVATION" oldelev)
      (command "._UCS" "_World")
      (list traysols fitsols (reverse skipped)))))
;; MEDMAKE3D tray stage entry: Solid Bottom (default) or Rungs per _TRAY3DBOTTOM
(defun med3d-tray-build-style ()
  (if (med3d-tray-rungs-p) (med3d-ladder-build) (med3d-tray-build)))
(princ "Done.")
