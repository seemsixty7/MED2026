;; MEDRouteTest.lsp - helpers for MEDRouteTest.ps1
;; accoreconsole has no ActiveX: vlax-ename->vla-object returns nil. Test-only shims so the
;; existing SWEEP code (vla-put-Layer / bbox) runs; ActiveX-only PIECES fallback is not covered.
(vl-load-com)
(setq rt-com (vl-catch-all-apply 'vlax-get-acad-object nil))
(if (or (null rt-com) (vl-catch-all-error-p rt-com))
  (progn
    (princ "\n[RT] no ActiveX (core console): test shims on")
    (defun vlax-ename->vla-object (e) e)
    (defun vla-put-Layer (e lay / ed) (setq ed (entget e)) (entmod (subst (cons 8 lay) (assoc 8 ed) ed)))))
;; MASSPROP prints "Volume:" (the .ps1 shows it next to the [RT] line; no file in the console)
(defun rt-volume (e)
  (command "_.MASSPROP" e "")
  (while (= 1 (logand 1 (getvar "CMDACTIVE"))) (command "_N"))
  0.0)
(defun rt-geo (e / ed)
  (setq ed (entget e))
  (vl-remove-if-not '(lambda (g) (member (car g) '(0 10 42 70 38))) ed))
(defun rt-info (tag e / ed typ n b vs v)
  (setq ed (entget e) typ (cdr (assoc 0 ed)) n 0 b 0)
  (cond
    ((= typ "LWPOLYLINE")
      (foreach g ed (if (= (car g) 10) (setq n (1+ n))) (if (and (= (car g) 42) (/= (cdr g) 0.0)) (setq b (1+ b)))))
    ((= typ "POLYLINE")
      (setq v (entnext e))
      (while (= (cdr (assoc 0 (entget v))) "VERTEX") (setq n (1+ n) vs (cons (cdr (assoc 10 (entget v))) vs) v (entnext v)))))
  (princ (strcat "\n[RT] " tag ": " typ " flags " (itoa (if (assoc 70 ed) (cdr (assoc 70 ed)) 0)) " verts " (itoa n) " bulges " (itoa b)
                 (if vs (strcat " pts " (vl-princ-to-string (reverse vs))) "")
                 " width " (vl-princ-to-string (cdr (assoc 43 ed)))
                 " xdata " (if (xdataget e _CONDUIT) "CONDUIT" (if (xdataget e _CABLE) "CABLE" "none"))))
  e)
;; same geometry after shifting Y by 1000
(defun rt-cmp (a b / ga gb ok)
  (setq ga (rt-geo a) gb (rt-geo b) ok (= (length ga) (length gb)))
  (if ok (mapcar '(lambda (x y) (if (= (car x) 10)
                                  (if (not (equal (list (cadr x) (+ 1000.0 (caddr x))) (cdr y) 1e-6)) (setq ok nil))
                                  (if (not (equal x y 1e-6)) (setq ok nil)))) ga gb))
  (princ (strcat "\n[RT] 2D old vs new geometry: " (if ok "IDENTICAL" "DIFFERENT")))
  (if (not ok) (progn (princ "\n[RT] old ") (princ ga) (princ "\n[RT] new ") (princ gb))))
(defun rt-line ( / xd)
  (entmake '((0 . "LINE") (10 100000.0 3000.0 0.0) (11 100100.0 3000.0 60.0)))
  (xdatadd (entlast) (bld_conduit _CODE _CSIZE "LN1" nil "T"))
  (rt-info "LINE + conduit xdata" (entlast)))
(defun rt-solid (tag e kind / r sol vol len od)
  (med3d-begin "RT")
  (setq r (med3d-run e kind))
  (med3d-end)
  (if r
    (progn
      (setq sol (car r) vol (rt-volume sol)
            od (med3d-get "OD" (cadr r)) len 0.0)
      (foreach p (med3d-get "PIECES" (cadr r))
        (if (= (car p) "L") (setq len (+ len (distance (nth 1 p) (nth 2 p))))))
      (princ (strcat "\n[RT] " tag " solid: (Volume above) OD " (rtos od 2 3)
                     " centerline*area " (rtos (* len pi 0.25 od od) 2 2)
                     " sharp " (if (med3d-get "SHARP" (cadr r)) "Y" "N")
                     " corners " (vl-princ-to-string (mapcar '(lambda (c) (med3d-get "STATUS" c)) (med3d-get "CORNERS" (cadr r))))
                     " layer " (cdr (assoc 8 (entget sol))) " xdata " (if (xdataget sol _CONDUIT) "CONDUIT" "none"))))
    (princ (strcat "\n[RT] " tag " solid: NONE " (vl-princ-to-string *MED3D-SKIPS*)))))
(princ)
;; the HEAD CONDUIT drawing steps: PLINE through the points, then fillet "p"
(defun rt-oldsim (pts)
  (setvar "OSMODE" 0)
  (command "_.PLINE")
  (foreach p pts (command (list (float (car p)) (float (cadr p)))))
  (command "")
  (setvar "filletrad" (* _MEDRADFAC _CSIZE _PLOTSCALE))
  (command "fillet" "p" (list (entlast) (getvar "lastpoint")))
  (princ))
