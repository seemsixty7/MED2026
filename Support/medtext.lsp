(princ "\rLoading MEDText...")
(defun c:fd( / dwgcnt dwgnm dwg_info fileinfo currdate year month
                     day mnth_list jmonth hour minute dwgchar dwg ampm
                     dateinfo timinfo userinfo viewinfo all_info fileinfodata
                     oldinfo newinfo
                 )

  (setq currdate (rtos (getvar "CDATE") 2 8)    ;Get Current Date
        year     (substr currdate 1 4)          ;Get Year from Date
        month    (atoi (substr currdate 5 2))   ;Get integer of Month
        day      (substr currdate 7 2)          ;Get day from date
        fdupd nil
        mnth_list(list (cons 1  "January")      ;Create list of months
                       (cons 2  "February")     ;and associate to an integer
                       (cons 3  "March")
                       (cons 4  "April")
                       (cons 5  "May")
                       (cons 6  "June")
                       (cons 7  "July")
                       (cons 8  "August")
                       (cons 9  "September")
                       (cons 10 "October")
                       (cons 11 "November")
                       (cons 12 "December")
                 )
        jmonth   (cdr (assoc month mnth_list))  ;match julian month to int
        hour     (atoi (substr currdate 10 2))  ;Get Current Hour
        minute   (substr currdate 12 2)         ;Get Current Minutes
        dwgnm    (getvar "DWGNAME")             ;get dwg name
        dwgprefix(getvar "DWGPREFIX")           ;Get Path prefix
        dwglen   (strlen dwgnm)                 ;length of dwg name
        dwgcnt   0                              ;misc counter variable
  )
  (while (and (not dwg) (< dwgcnt dwglen))      ;while dwg is not defined
                                                ;and dwgcnt lessthan dwglen
     (setq dwgchar (substr dwgnm (- dwglen dwgcnt) 1));get a char from dwgnm
     (if (= dwgchar "\\")                       ;is it the \\ char
        (setq dwg  (substr dwgnm (- dwglen (1- dwgcnt))));if so set dwg
     )
     (setq dwgcnt (1+ dwgcnt))                  ;add one to dwgcnt
  )
  (if (not dwg)                                 ;does dwg exist
    (setq dwg dwgnm)                            ;if not assign dwg dwgnm
  )
  (if _FDFULLPATH
     (setq dwg (strcat dwgprefix dwg))
  )
  (if (>= hour 12)                              ;is hour am or pm
     (progn                                     ;setq ampm to pm
        (setq ampm "PM")                        ;if hour isn'nt 12:00
        (if (/= hour 12.0)                      ;subtract 12 hours
           (setq hour (- hour 12))
        )
     )
     (setq ampm "AM")                           ;else set to am
  )
  (setq hour (itoa (fix hour)))                 ;convert hour to string
  (setq dateinfo (strcat jmonth " " day ", " year " ");cretae date part
        timeinfo (strcat hour ":" minute " " ampm " ");create time part
        userinfo (getvar "loginname")           ;get userinfo
        dwg_info dwg                            ;assign dwg_info to dwg
        dwg_scl  (strcat "1=" (rtos _SC 2))     ;combine all data into 1 string
        all_info (strcat "FILE INFO: "
                         dwg_info " "
                         dwg_scl " "
                         dateinfo
                         timeinfo userinfo)
  )
  (setq fdss (ssget "X" (list (cons 0 "INSERT") (cons 2 _FDBLOCK))))
  (if _FDALLCAPS (setq all_info (strcase all_info)))
  (if fdss
    (progn
      (setq cnt 0
            num (sslength fdss)
      )
      (while (< cnt num)
        (setq hdent  (ssname fdss cnt)
              atent  (sel_att_ent hdent _FDATT all_info)
              hddata (entget hdent)
              oldlay (assoc 8 hddata)
              newlay (cons 8 (nth 0 _FDTEXT))
              hddata (subst newlay oldlay hddata)
        )
        (entmod hddata)
        (if atent
          (progn
            (setq atdata (entget atent)
                  oldlay (assoc 8 atdata)
                  newlay (cons 8 (nth 0 _FDTEXT))
                  atdata (subst newlay oldlay atdata)
                  fdupd T
            )
            (if (setq oldlay (assoc 62 atdata))
               (progn
                  (setq newlay (cons 62 256)
                        atdata (subst newlay oldlay atdata)
                  )
               )
            )
            (entmod atdata)
            (entupd hdent)
          )
        )
        (setq cnt (1+ cnt))
      )
    )
  )
  (if (not fdupd)
    (progn
      (princ)
      (prompt (strcat "\n"  _FDBLOCK " block not found! "))
      (if _FDDEFAULTINS
	(setq plac (nth 0 _FDDEFAULTINS)
	      fdro (nth 1 _FDDEFAULTINS)
	)
	(setq plac (getpoint "\nSelect Insertion Point: ")
	      fdro (getangle plac "\nAngle of insertion: ")
	)
      )
      (if (not fdro)
        (setq fdro 0.0)
      )
      (smlayer _FDTEXT)
      (setq curattdia (getvar "attdia")
	    curattreq (getvar "attreq")
      )
      (setvar "attdia" 0)
      (setvar "attreq" 0)
      (command ".insert" (strcat _FDBLOCK "=") plac (* 1.0 _SC) "" (angtos fdro 0))
      (setvar "ATTDIA" curattdia)
      (setvar "attreq" curattreq)
      (sel_att_ent (entlast) _FDATT all_info)
      (progn
        (setq hdent  (entlast)
              atent  (entnext hdent)
              atdata (entget atent)
              oldlay (assoc 8 atdata)
              newlay (cons 8 (nth 0 _FDTEXT))
              atdata (subst newlay oldlay atdata)
              fdupd T
        )
        (if (setq oldlay (assoc 62 atdata))
           (progn
              (setq newlay (cons 62 256)
                    atdata (subst newlay oldlay atdata)
              )
           )
        )
        (entmod atdata)
        (entupd hdent)
      )


    )
  )
  (princ)
)

(defun c:xt( / ans sbpt num count ss1 hgt new wdth styl nhgt cur ent old old1
               old3)
    (med_cur_set "c:xt")
    (prompt "\nSelect text entities to be converted: ")
    (setq ss1 (ssget)
          count 0
          num (sslength ss1)
    )
    (terpri)
    (setq styl (getstring "\nStyle name to convert to: "))
    (if (not (tblsearch "STYLE" styl))
       (progn
         (setvar "cmdecho" 1)
         (prompt "\nStyle name not defined. Please define it\n")
	 (command "style" styl pause pause pause pause pause pause pause)  
	 (setvar "cmdecho" 0)
       )
    )
    (setq hgt (assoc 40 (tblsearch "STYLE" styl))
          new (cons 7 styl)
          wdth (assoc 41 (tblsearch "STYLE" styl))
    )
    (if (= (cdr hgt) 0.0)
      (progn
                 (prompt "\nText style height is 0.0")
        (setq nhgt (getdist (strcat "\nText height<" (rtos (getvar "textsize"))">:")))
        (if nhgt
           (setq hgt (cons 40 nhgt))
           (setq hgt (cons 40 (getvar "textsize")))
        )
      )
    )
    (initget "Yes No")
    (setq ans (getkword "\nAdjust group for spacing Y/N:<N> "))
    (if (not (or (not ans) (= ans "No")))
      (progn
       (setq sbpt (getpoint "\nBase point"))
       (while (< count num)
         (setq cur (ssname ss1 count))
         (if (= (dxf 0 (entget cur)) "TEXT")
           (command "scale" cur "" sbpt "r" (dxf 40 (entget cur)) (cdr hgt))
         )
         (setq count (1+ count))
       )
       (setq count 0.0)
       )
 
     )
    (while (< count num)
         (setq cur (ssname ss1 count))
         (setq ent (entget cur))
         (if (= (cdr (assoc 0 ent)) "TEXT")
              (progn
                  (setq old (assoc 7 ent)
                         ent (subst new old ent)
                         old1 (assoc 40 ent)
                         ent (subst hgt old1 ent)
                         old3 (assoc 41 ent)
                         ent (subst wdth old3 ent) 
                  )
                   (entmod ent)

         )     )
         (setq count (1+ count))
    )
    (setvar "highlight" 0)
    (command "select" ss1 "")
    (setvar "highlight" 1)
    (med_ret_ok)
    (princ)
)

(defun c:upcase ( / count ent new old old1 ss1 txt)
   (setq count 0)
   (prompt "\nSelect text to be converted to UPPERCASE: ")
   (setq ss1 (ssget)
         len (sslength ss1)
   )
   (while (< count len)
          (setq txt (ssname ss1 count)
                ent (entget txt)
          )
	  (if (= (dxf 0 ent) "TEXT")
	    (progn (setq old (assoc 1 ent)
                   old1 (cdr old)
                   new (cons 1 (strcase old1))
             )
             (setq ent (subst new old ent))
             (entmod ent)
	    )
	  )  
          (setq count (1+ count))
     )
   (prompt "\nThats it!!")
   (princ)
)
(defun c:rt( );/ ss1 num count edata ename newtext oldtext)
    (prompt "\nSelect text to be replaced: ")
    (setq ss1 (ssget)
          num (sslength ss1)
          count 0
          edata nil
          ename nil
          nt nil
    )
    (setq newvalue (nentsel "\nSelect New Value - [Press Enter to Type New Value]: "))
	(if newvalue
		(progn
			(setq entdata (entget (car newvalue))
				  txtdata (assoc 1 entdata)
			)
			(if txtdata
				(progn
					(setq newtext (dxf 1 entdata))
				)
				(progn
					(prompt "\nObject selected does not have any data to copy!")
					(setq newtext (getstring "\nNew Value: "))
				)
			)
		)
		(setq newtext (getstring "\nNew Value: "))
	)
    (while (< count num)
         (setq ename (ssname ss1 count))
         (setq edata (entget ename))
         (if (= (cdr (assoc 0 edata)) "TEXT")
              (progn
                   (setq oldtext (assoc 1 edata)
                         edata (subst (cons 1 newtext) oldtext edata)
                   )
                   (entmod edata)
              )
         )
         (setq count (1+ count))
    )
    (princ)

)

(defun c:ct( / num count ss1 item inp ent new old)
    (med_cur_set "C:CT")
    (setvar "cmdecho" 0)
    (setq ss1 (ssget)
          num (sslength ss1)
          count 0
    )
    (while (< count num)
           (setq item (ssname ss1 count)
                 ent (entget item)
           )
            (if (= (cdr (assoc 0 ent)) "TEXT")
              (progn
                   (command "select" item)
                   (setq inp 
                       (getstring T (strcat "\nNew text:<" (dxf 1 ent) ">: ")))
                   (command nil)
                   (if (= inp "")
                       (setq inp (dxf 1 ent))
                   )
                   (setq new (cons 1 inp))
                   (setq old (assoc 1 ent)
                         ent (subst new old ent)
                   )
                   (entmod ent)
           )   )
          (setq count (1+ count))
    )
    (med_ret_ok)
    (princ)
)

(defun c:acx ( / pt ptlist old hlmode new)
    (med_cur_set "c:acx")
    (setq hlmode (getvar "highlight"))
    ;(setvar "highlight" 0)
    (setvar "cmdecho" 0)
    (prompt "\nFor window selection hit return for attribute selection. ")
    (while (setq pt (cadr (nentsel "\nSelect attributes to change: ")))
           (setq ptlist (append ptlist (list pt))
    )      )
    (princ)
    (setq old (getstring T "old string: ")
          new (getstring T "new string: ")
    )
    (if ptlist
             (progn
             (command "attedit" "n" "" "" "" ""
                      (foreach pt ptlist (command pt)
                      "")
                       old new )
             )
             (progn
             (setvar "cmdecho" 1)
             (command "attedit" "n" "" "" "" "" "w" pause pause old new)
    )        )
    (princ)
    (setvar "cmdecho" 1)
    ;(setvar "highlight" hlmode)
    (med_ret_ok)
    (princ)
)

(defun c:ac (/ old )
  (setq old AC_VAL)
  (if old 
    (setq AC_VAL (getstring T (strcat "\nEnter new value:<" old ">:")))
    (setq AC_VAL (getstring T "\nEnter new value: "))
  )
  (if (= AC_VAL "")
   (setq AC_VAL old)
  )
  (prompt "\nSelect Attribute: ")
  (command "attedit" "" "" "" "" pause "" "v" "" AC_VAL "")
  (princ)
)
(defun c:ctedit()
    (med_cur_set "c:ctedit")
    (if (not CTEDITSS)
      (progn
        (setq ss1 (ssget))
      )
      (progn
        (setq ss1 CTEDITSS)
      )
    )
    (setq numb (sslength ss1)
          count 0
    )
    (sets)
    (while (< count numb)
           (setq item (ssname ss1 count)
                 ent (entget item)
           )
            (if (= (cdr (assoc 0 ent)) "TEXT")
              (progn
                   (command "select" item)
                       (ntext)
                   (command nil)
                   (if (= inp "")
                       (setq inp (dxf 1 ent))
                   )
                   (setq new (cons 1 inp))
                   (setq old (assoc 1 ent)
                         ent (subst new old ent)
                   )
                   (entmod ent)
           )   )
          (setq count (1+ count))
    )
    (setq preval nil
          sufval nil
          pre nil
          suf nil
          prenum nil
          sufnum nil
          num nil
          sufst nil
          prest nil
          inp nil
          prean nil
          sufan nil
          CTEDITSS nil
    )
    (med_ret_ok)
    (princ)
)
(defun update(var cntr)
  (if (< (ascii var) 58)
      (setq num (atoi var)
            num (itoa (+ num cntr)))
      (setq num (ascii var)
            num (chr (+ num cntr))
      )
  )
  num
)
(defun ntext()
  (setq inp (dxf 1 ent))
  (if preval
    (progn
      (setq inp (strcat preval (substr inp (1+ prenum))))
      (if prest
        (setq preval (update preval precnt))
      )
    )
  )
  (if sufval
    (progn
      (setq inp (strcat (substr inp 1 (- (strlen inp) sufnum)) sufval))
      (if sufst
        (setq sufval (update sufval sufcnt))
      )
    )
  )
  (if (and (not preval) (not sufval))
   (progn
     (if pre
       (setq inp (strcat (getstring T "\nPrefix: ") (substr inp (1+ prenum))))
     )
     (if suf
       (setq inp (strcat (substr inp 1 (- (strlen inp) sufnum)) (getstring T "\nSuffix: ")))
     )
     (if (and (not suf)(not pre))
       (setq inp (getstring T (strcat "\nNew text:<" (dxf 1 ent) ">: ")))
     )
   )
  )
)
(defun edadd(typedata / edans ret)
  (initget 1 "Edit Add")
  (setq edans (getkword (strcat "\nEdit or Add " typedata ": ")))
  (if (= edans "Edit")
    (setq ret (getint "\nNumber of Characters to edit: "))
    (setq ret 0)
  )
  ret
)
(defun sets()
  (setq ans "null")
  (while (/= ans "Change")
    (initget "Change Prefix Suffix")
    (setq ans (getkword "\nChange/Prefix/Suffix <Change>: "))
    (cond ((= ans "Prefix")
           (setq prenum(edadd "Prefix"))
             (initget "Single Multiple")
             (setq pre (getkword "\nSingle or Multiple edit: "))
             (if (= pre "Multiple")
               (progn
                 (initget 1 "Autostep Typical")
                 (setq prean (getkword "\nAutostep Or Typical: "))
                 (if (= prean "Autostep")
                   (setq prest(getstring T "Start point: ")
                         precnt(getint "Counter step: ")
                         preval prest
                     )
                     (setq preval (getstring T "\nPrefix: "))
                 )
               )
               (setq pre T)
             )
            )
            ((= ans "Suffix")
           (setq sufnum(edadd "Suffix"))
             (initget "Single Multiple")
             (setq suf (getkword "\nSingle or Multiple edit: "))
             (if (= suf "Multiple")
               (progn
                 (initget 1 "Autostep Typical")
                 (setq sufan (getkword "\nAutostep Or Typical: "))
                 (if (= sufan "Autostep")
                   (setq sufst(getstring T "Start point: ")
                         sufcnt(getint "Counter step: ")
                         sufval sufst
                     )
                     (setq sufval (getstring T "\nSuffix: "))
                 )
               )
               (setq suf T)
             )
            )
            ((not ans)
              (setq ans "Change")
            )
    )        
  )
)
;changes text entities justification and aligns text strings
;to a selected point based on justification
(defun c:tj()
    (med_cur_set "C:TJ")
    (setvar "cmdecho" 0)
    (prompt "\nSelect text entities to be converted: ")
    (setq ss1 (ssget)
          count 0
          num (sslength ss1)
    )
    (initget 1 "Left MLeft TLeft Center Middle TCenter Right MRight TRight")
    (setq just (getkword "Justification of Text: L/ML/TL/C/M/TC/R/MR/TR: ")
          align (car (getpoint "Pick point for text to align by justification:"))
    )
    (if (= just "Left")
        (setq new (cons 72 0)
              new1(cons 73 0))
    )
    (if (= just "Right")
        (setq new (cons 72 2)
              new1(cons 73 0))
    )
    (if (= just "Center")
        (setq new (cons 72 1)
              new1(cons 73 0))
    )
    (if (= just "Middle")
        (setq new (cons 72 1)
              new1(cons 73 2))
    )
    (if (= just "MLeft")
        (setq new (cons 72 0)
              new1(cons 73 2))
    )
    (if (= just "MRight")
        (setq new (cons 72 2)
              new1(cons 73 2))
    )
    (if (= just "TLeft")
        (setq new (cons 72 0)
              new1(cons 73 3))
    )
    (if (= just "TCenter")
        (setq new (cons 72 1)
              new1(cons 73 3))
    )
    (if (= just "TRight")
        (setq new (cons 72 2)
              new1(cons 73 3))
    )
    (while (< count num)
         (setq cur (ssname ss1 count))
         (setq ent (entget cur))
         (if (= (cdr (assoc 0 ent)) "TEXT")
              (progn
                   (setq old (assoc 72 ent)
                         ent (subst new old ent)
                         old1 (assoc 73 ent)
                         ent (subst new1 old1 ent)
                   )
                   (entmod ent)
                   (setq gettj (entget (dxf -1 ent)))
                   (if (= just "Left")
                       (progn
                           (setq y10 (cadr (dxf 10 ent))
                                 pt10 (list align y10 0)
                           )
                           (tjupd pt10 nil)
                       )
                       (progn
                           (if (equal (dxf 11 ent) '(0.0 0.0 0.0))
                               (setq y11 (cadr (dxf 10 ent)))
                               (setq y11 (cadr (dxf 11 ent)))
                           )
                           (setq pt11 (list align y11 0)
                                 ptdist(distance (dxf 10 gettj) (dxf 11 gettj))
                                 tjang(angle (dxf 10 gettj) (dxf 11 gettj))
                                 pt10 (polar pt11 tjang ptdist)
                           )
                           (tjupd pt10 pt11)
                       )
                   )
         )     )
         (setq count (1+ count))
    )
    (med_ret_ok)
    (prompt "\nThat's it!!")(princ)
)
(defun tjupd (pt1 pt2)
   (if pt2
      (progn
        (setq tjw (cons 10 pt1)
              tjw1 (cons 11 pt2)
              tjd (assoc 10 ent)
              tjd1 (assoc 11 ent)
              ent (subst tjw tjd ent)
              ent (subst tjw1 tjd1 ent)
        )
      )
      (progn
        (setq tjw(cons 10 pt1)
              tjd (assoc 10 ent)
              ent(subst tjw tjd ent)
        )
       )
   )
   (entmod ent)
)

(defun c:ut( / ulss ulsslen ulcnt uldata)
 (prompt "\nSelect text entities to be underlined.")
 (setq ulss    (ssget)
       ulsslen (sslength ulss)
       ulcnt   0
 )
 (while (< ulcnt ulsslen)
    (setq ulent (ssname ulss ulcnt)
          uldata(entget ulent)
    )
    (if (= (dxf 0 uldata) "TEXT")
       (progn
         (setq ulval (dxf 1 uldata)
               ulval (strcat "%%u" ulval)
               uldata(subst (cons 1 ulval) (assoc 1 uldata) uldata)
         )
         (entmod uldata)
       )
    )
    (setq ulcnt (1+ ulcnt))
 )
 (princ)
)
(defun c:cx( / cxss cxlen cxcnt cxfirst cxoldst cxoldln cxnewst cxnewln
               cxdata oldval newval chngd)
  (med_cur_set "C:CX")
  (prompt "\nSelect text to be changed: ")
    (setq cxss (ssget))
    (if cxss
       (progn
          (setq cxlen   (sslength cxss)
                cxcnt   0
                cxfirst (entget (ssname cxss 0))
          )
          (while (/= (dxf 0 cxfirst) "TEXT")
              (setq cxcnt (1+ cxcnt)
                    cxfirst (entget (ssname cxss cxcnt))
              )
          )
          (setq cxcnt 0
                cxoldst (getstring T (strcat "\nOld String:["
                                           (dxf 1 cxfirst) "] "))
                cxoldln (strlen cxoldst)
                cxnewst (getstring T "\nNew String: ")
                cxnewln (strlen cxnewst)
          )
          (cond
             
             ((and (= cxoldln 0) (= cxnewln 0))
                 (prompt "\nNothing to do!")
             )

             ((= cxoldln 0)
                 (while (< cxcnt cxlen)
                    (setq cxdata (entget (ssname cxss cxcnt)))
                    (if (= (dxf 0 cxdata) "TEXT")
                        (progn
                           (setq oldval (assoc 1 cxdata)
                                 newval (strcat cxnewst (dxf 1 cxdata))
                                 newval (cons 1 newval)
                                 cxdata (subst newval oldval cxdata)
                           )
                           (entmod cxdata)
                        )
                    )
                    (setq cxcnt (1+ cxcnt))
                 )
             )

             ((> cxoldln 0)
                 (while (< cxcnt cxlen)
                    (setq cxdata (entget (ssname cxss cxcnt)))
                    (if (= (dxf 0 cxdata) "TEXT")
                        (progn
                           (setq oldval (dxf 1 cxdata)
                                 oldlen (strlen oldval)
                                 oldcnt 0
                                 newval ""
                                 chngd nil
                           )
                           (while (< oldcnt oldlen)
                              (setq cmpval (substr oldval (1+ oldcnt) cxoldln))
                              (if (= cmpval cxoldst)
                                 (progn
                                   (setq newval (strcat newval cxnewst)
                                         oldcnt (1- (+ oldcnt cxoldln))
                                         chngd T
                                   )

                                 )
                                 (progn
                                   (setq newval (strcat newval (substr oldval (1+ oldcnt) 1)))
                                 )
                              )
                              (setq oldcnt (1+ oldcnt))
                           )
                           (if chngd
                              (progn
                                (setq newval (cons 1 newval)
                                      oldval (assoc 1 cxdata)
                                      cxdata (subst newval oldval cxdata)
                                )
                                (entmod cxdata)
                              )
                           )
                        )
                    )
                    (setq cxcnt (1+ cxcnt))
                 )
             )
          )
       )
    )
    (princ)
    (med_ret_ok)
)
(defun c:atadd()
  (setq blkent(car (entsel "\nSelect Block to Add Attribute to: "))
        tagnm (getstring "\nTAG: ")
        atval (getstring T "\nValue: ")
        inspt (getpoint "\nSelect Point for Insertion of Attribute: ")
        blkdata (entget blkent (list"*")) 
  )
  (initget 1 "Left MLeft TLeft Center Middle TCenter Right MRight TRight")
  (setq just (getkword "Justification of Text: L/ML/TL/C/M/TC/R/MR/TR: ")
        align (car (getpoint "Pick point for text to align by justification:"))
  )
  (if (= just "Left")
      (setq new (cons 72 0)
            new1(cons 73 0))
  )
  (if (= just "Right")
      (setq new (cons 72 2)
            new1(cons 73 0))
  )
  (if (= just "Center")
      (setq new (cons 72 1)
            new1(cons 73 0))
  )
  (if (= just "Middle")
      (setq new (cons 72 1)
            new1(cons 73 2))
  )
  (if (= just "MLeft")
      (setq new (cons 72 0)
            new1(cons 73 2))
  )
  (if (= just "MRight")
      (setq new (cons 72 2)
            new1(cons 73 2))
  )
  (if (= just "TLeft")
      (setq new (cons 72 0)
            new1(cons 73 3))
  )
  (if (= just "TCenter")
      (setq new (cons 72 1)
            new1(cons 73 3))
  )
  (if (= just "TRight")
      (setq new (cons 72 2)
            new1(cons 73 3))
  )

  (if (= (dxf 66 blkdata) 1)
    (progn
       (entmake blkdata)
       (setq suben (entnext blkent)
             subdata (entget suben)
       ) 
       (while (/= (dxf 0 subdata) "SEQEND")
         (entmake subdata)
         (setq suben (entnext suben)
               subdata (entget suben)
         )
       )
    )
    (progn
       (setq newblk (list (cons 0 "INSERT")
                          (assoc 10 blkdata)
                          (assoc 2 blkdata)
                          (assoc 41 blkdata)
                          (assoc 8 blkdata)
                          (assoc 42 blkdata)
                          (assoc 43 blkdata)
                          (assoc 50 blkdata)
                          (cons 66 1)
                    )
       )
       (if (assoc -3 blkdata)
           (setq newblk (append newblk (list (assoc -3 blkdata))))
       )
       (entmake newblk)
    )
  )
  (setq addent (list (cons 0 "ATTRIB")
                     (cons 8 (nth 0 _MEDTEXT))
                     (cons 70 0)
                     (cons 10 inspt)
                     (cons 1 atval)
                     (cons 2 tagnm)
                     (cons 40 (getvar "TEXTSIZE"))
                     (cons 7  (getvar "TEXTSTYLE"))
               )
  )
  (entmake addent)
  (entdel blkent)
  (entmake (list (cons 0 "SEQEND")))
)

;;;This was the start of a dialog based CTEDit command. Not a bad idea to complete this.
;(defun c:nce()
;    (med_cur_set "c:ctedit")
;    (if (not CTEDITSS)
;      (progn
;        (setq ss1 (ssget))
;      )
;      (progn
;        (setq ss1 CTEDITSS)
;      )
;    )
;    (setq numb (sslength ss1)
;          count 0
;    )
;   (if (> (setq index_val (load_dialog "med")) 0)
;      (progn
;         (if (new_dialog "Med_CTEdit" index_val)
;            (progn 
;                (action_tile "Prefix" )
;                (action_tile "accept" "(done_dialog 1)")
;                (action_tile "cancel" "(done_dialog 0)")
;
;                (setq result (start_dialog))
;            )
;         )
;         (unload_dialog index_val)
;         (if (= result 1)
;            (princ "go")
;         )
;      )
;   )
;   (princ)
;)

 
;(defun medleader(leadblname txtflag scalesz / lay txt genang lentmrk lentbk pt pt1 entblk allss entdata
;                 oldy newy txt)
;     (setq genang nil)
;     (setq lay (getvar "clayer"))
;     (setq acvr (atoi (getvar "ACADVER")))
;     (smlayer _MEDTEXT)
;     (setq scalesz (* scalesz 1.0))
;     (if leadblname
;       (progn
;          (if (not (tblsearch "BLOCK" leadblname))
;            (command "insert" leadblname nil)
;          )
;          (setq lentmrk(entlast))
;          (while lentmrk
;             (setq lentbk lentmrk
;                   lentmrk (entnext lentmrk)
;             )
;          )
;	  
;	  (if (>= acvr	15)
;	    (command "dim" "dimldrblk" leadblname "dimasz" (* _LEADSYMSIZE scalesz) "leader")
;	    (command "dim" "dimblk" leadblname "dimasz" (* _LEADSYMSIZE scalesz) "leader")
;	  )
;       )
;       (progn
;	 (if (>= acvr 15)
;	   (command "dim" "dimldrblk" "." "dimasz" (* _LEADSYMSIZE scalesz) "leader")
;           (command "dim" "dimblk" "." "dimasz" (* _LEADSYMSIZE scalesz) "leader")
;	 )
;       )
;     )
;	 (setq pt (getpoint "\nLeader start: ")
;           pt1 pt
;     )
;	 (command pt)
;	 (while 
;	   (setq pt (getpoint pt "\nto: "))
;       (if (not genang)
;         (setq genang (angle pt1 pt))
;       )
;	   (command pt)
;	 )
;     (command "")
;     (if leadblname 
;       (progn
;          (if (and (<= genang (* PI 1.5)) (> genang (* PI 0.5)))
;             (progn
;                (if (not lentbk)
;                  (setq entblk (ssname (setq allss (ssget "X"))
;                                       (1- (sslength allss))
;                               )
;                  )
;                  (setq entblk (entnext lentbk))
;                )
;                (setq entdata(entget entblk)
;                      oldy   (assoc 42 entdata)
;                      newy   (cons 42 (* (dxf 42 entdata) -1))
;                      entdata(subst newy oldy entdata)
;                )
;                (entmod entdata)
;             )
;          )
;        )
;      )
;      (if txtflag
;        (progn
;           (setq txt (getstring T "\nText: "))
;           (if (= txt "")
;             (command nil)
;             (command txt)
;           )
;        )
;        (progn
;           (command nil)
;        )
;      )
;      (if (>= acvr 15)
;	(command "dimldrblk" "." "dimasz" _LEADSYMSIZE "exit")
;	(command "dimblk" "." "dimasz" _LEADSYMSIZE "exit")
;      )
;     (command "layer" "s" lay "")
;     (princ)
;)


(defun c:mt()
  (prompt "\nSelect Text Objects to be changed: ")
  (setq chgss (ssget (list (cons 0 "TEXT")))
	mstent nil	 
  )
  (if chgss
   (progn
     (while (not mstent)
       (setq mstent (entsel "\nSelect Master Text Entity"))
       (if mstent
	 (progn
	   (setq mstent (entget (car mstent)))
	   (if (/= (dxf 0 mstent) "TEXT")
	     (progn
	       (setq mstent nil)
	       (prompt "\nEntity must be a text entity: ")
	     )
	   )
	 )
	 (prompt "\nYou must select a text entity: ")
       )
     )
     (if (not MT_MATCHLIST)
       (setq MT_MATCHLIST (list (cons 7 0) (cons 40 0) (cons 51 0) (cons 41 0) (cons 50 0)))
     )
     (setq tmplist MT_MATCHLIST)
     (if (> (setq index_val (load_dialog "med")) 0)
      (progn
         (if (new_dialog "Match_Text" index_val)
            (progn
	        (set_tile "mStyle" (itoa (dxf 7 tmplist)))
	        (set_tile "mHeight" (itoa (dxf 40 tmplist)))
	        (set_tile "mOblique" (itoa (dxf 51 tmplist)))
	        (set_tile "mWidth" (itoa (dxf 41 tmplist)))
	        (set_tile "mRotation" (itoa (dxf 50 tmplist)))
	      
                (action_tile "mStyle"    "(setq tmplist (listtoggle tmplist 7))")
                (action_tile "mHeight"   "(setq tmplist (listtoggle tmplist 40))")
	        (action_tile "mOblique"  "(setq tmplist (listtoggle tmplist 51))")
	        (action_tile "mWidth"    "(setq tmplist (listtoggle tmplist 41))")
	        (action_tile "mRotation" "(setq tmplist (listtoggle tmplist 50))")
                (setq result (start_dialog))
            )
         )
         (unload_dialog index_val)
         (if (= result 1)
            (progn
	      (setq MT_MATCHLIST tmplist)
	      (matchtxtprops chgss MT_MATCHLIST mstent)
	    )
         )

      )
     )
   )
   (prompt "\nNo text selected:")
  )
  (princ)
)

(defun matchtxtprops (mtchss chglist mstrdata)
  (setq chgdata nil)
  (foreach itm chglist
    (if (= (cdr itm) 1)
      (setq chgdata (append chgdata (list (assoc (car itm) mstrdata))))
    )
  )
  (setq num (sslength mtchss)
        cnt 0
  )
  (while (< cnt num)
    (setq ent (ssname mtchss cnt)
          data(entget ent)
	  cnt (1+ cnt)
    )
    (foreach itm chgdata
      (setq oldvals (assoc (car itm) data)
	    data    (subst itm oldvals data)
      )
    )
    (entmod data)
  )
)

(defun grldr(pt numpk blnm scadj)
  (setq genang nil)
  (if blnm
    (progn
      (if (not (tblsearch "BLOCK" blnm))
	 (command "insert" blnm nil)
      )
    )
  )
  (setq lentmrk(entlast))
  (while lentmrk
     (setq lentbk lentmrk
	   lentmrk (entnext lentmrk)
     )
  )
  (command "dim")
  (if blnm
    (command "dimblk" blnm)
  )
  (command "dimasz" (* (getvar "dimasz") scadj 1.0) "leader")
  (if pt
    (setq pt1 pt)
    (setq pt (getpoint "\nLeader start: ")
	pt1 pt
    )
  )
  (command pt)
  (setq cnt 0)
  (while (and (< cnt numpk) (setq pt (getpoint pt "\nto: ")))
    (if (not genang)
      (setq genang (angle pt1 pt))
    )
   (command pt)
   (setq cnt (1+ cnt))
  )
  (command nil)
  (command "dimblk" "." "dimasz" (* (getvar "dimasz") (/ 1.0 scadj) 1.0) "exit")
  (command "layer" "s" lay "")

  (if (if blnm (= (strcase blnm) "GRABIT"))
    (progn
      (if (and (<= genang (* PI 1.5)) (> genang (* PI 0.5)))
	 (progn
	    (if (not lentbk)
	      (setq entblk (ssname (setq allss (ssget "X"))
				   (1- (sslength allss))
			   )
	      )
	      (setq entblk (entnext lentbk))
	    )
	    (setq entdata(entget entblk)
		  oldy   (assoc 42 entdata)
		  newy   (cons 42 (* (dxf 42 entdata) -1))
		  entdata(subst newy oldy entdata)
	    )
	    (entmod entdata)
	 )
      )
    )
  )
  (entlast)
)

;; Attcopy for Revisions and whatever else
(defun c:attcopy()
  (setq patt (nentsel "\nSelect Attribute to Copy: "))
  (if patt
     (progn
        (setq pdata (entget (car patt))
              satt  (nentsel "\nSelect Attribute to copy to: ")
              sdata (entget (car satt))
              ment  (getmainent (car satt))
              pval  (dxf 1 pdata)
              sdata (subst (cons 1 pval) (assoc 1 sdata) sdata)
        )
        (entmod sdata)
        (entupd ment)
     )
  )
)
(defun getmainent(subent)
   (while (/= (dxf 0 (entget subent)) "SEQEND")
       (setq subent (entnext subent))
   )
   (setq retent (dxf -2 (entget subent)))
)

(defun c:LOADTXT()
	(setvar "REGENMODE" 0)
	(setvar "CMDECHO" 0)
	(foreach TextStyleToCreate MED_TXT_STYLE_MAP
		(command "STYLE" (nth 1 TextStyleToCreate)
			             (nth 2 TextStyleToCreate)
			             (* _SC _PLOTSCALE (nth 3 TextStyleToCreate))
			             (nth 4 TextStyleToCreate)
			             (nth 5 TextStyleToCreate)
			             (nth 6 TextStyleToCreate)
			             (nth 7 TextStyleToCreate)
			             (nth 8 TextStyleToCreate)
	   )
	)
	(C:BLDSTL)
	(princ "\nText Styles Now Loaded")
	(princ)
)
(princ "Done.")
