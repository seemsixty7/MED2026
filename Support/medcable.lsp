(princ "\rLoading MEDCable...")
;; Draw body used by CABLE.
(defun med-cable-draw ( / conent conpt conqty cabtag cabreltag ptprompt xdlist route)
    (setvar "cmdecho" 0)
    (command "linetype" "s" _LTP "")
    (setq ptprompt (strcat "\nPick start point of "
                           (clookup _CABCODE _CABNUM _CABLE) ": ")
          route (med-route-draw ptprompt nil)
    )
    (if (not route) (progn (med_ret_ok) (exit)))
    (if (not _TAGOFF)
      (setq cabtag (getstring T "\nCable Tag number <NONE>: "))
      (setq cabtag "NONE")
    )
    (if (= cabtag "")
       (setq cabtag "NONE")
    )
    (if (not _TAGOFF)
      (setq cabreltag (getstring T "\nCable Relate Tag <NONE>: "))
      (setq cabreltag "NONE")
    )
    (if (= cabreltag "")
       (setq cabreltag "NONE")
    )
    (if (not (cadr route)) (chg_tray_pl_wdth (entlast) _CONPLWIDTH))
    (setq xdlist (bld_cable _CABCODE _CABNUM cabtag cabreltag nil "T"))
    (xdatadd (entlast) xdlist)
    (princ)
    (med_ret_ok)
    (terpri)
)
(defun c:cable ( / )
    (med_cur_set "c:cable")
    (if (member (type MED-CableApplyLayer) '(EXRXSUBR SUBR USUBR EXSUBR))
        (vl-catch-all-apply 'MED-CableApplyLayer)
    )
    (med-cable-draw)
)
(defun c:run3dcable ( / conent conpt conqty cabtag cabreltag ptprompt xdlist route)
    (med_cur_set "c:run3dcable")
    (if (member (type MED-CableApplyLayer) '(EXRXSUBR SUBR USUBR EXSUBR))
        (vl-catch-all-apply 'MED-CableApplyLayer)
    )
    (setvar "cmdecho" 0)
    (command "linetype" "s" _LTP "")
    ;; always a 3DPOLY (no Mode prompt); Elev / Undo at the point prompts
    (setq ptprompt (strcat "\nPick start point of "
                           (clookup _CABCODE _CABNUM _CABLE) ": ")
          route (med-route-draw ptprompt "3D")
    )
    (if (not route) (progn (med_ret_ok) (exit)))
    (if (not _TAGOFF)
      (setq cabtag (getstring T "\nCable Tag number <NONE>: "))
      (setq cabtag "NONE")
    )
    (if (= cabtag "")
       (setq cabtag "NONE")
    )
    (if (not _TAGOFF)
      (setq cabreltag (getstring T "\nCable Relate Tag <NONE>: "))
      (setq cabreltag "NONE")
    )
    (if (= cabreltag "")
       (setq cabreltag "NONE")
    )
    (chg_tray_pl_wdth (entlast) _CONPLWIDTH)
    (setq xdlist (bld_cable _CABCODE _CABNUM cabtag cabreltag nil "T"))
    (xdatadd (entlast) xdlist)
    ;; MEDProperties CABLE on 3D polyline (ObjectType in schema; no solid exporter)
    (MEDStamp3DFromBom (entlast) (entlast) "CABLE" nil)
    (princ)
    (med_ret_ok)
    (terpri)
)
(princ "Done.")
