(princ "\rLoading MEDUtil...")
;;;MED Primary utility function and commands file
;;;Copyright Moore Design (c) 1992-2013


(defun c:lbreak( / lay ent selpt data pt1 pt2 ptlist stang endang nlen
                   val40 val41 stpt vtxt1 vtxt2 vtxt3 sqend)
   (med_cur_set "C:LBREAK")
   (setq ent    (entsel "\nSelect entity to break")
         selpt  (osnap (cadr ent) "NEA")
         ent    (car ent)
         data   (entget ent)
         pt1    (getpoint "\nPick 1st point of break: ")
         pt2    (getpoint "\nPick 2nd point of break: " pt1)
   )
   (if pt2
     (progn
       (setq ptlist (list pt1 pt2))
       (command "break" (list ent pt1) "F" pt1 pt2)
       (setq stang  (+ (* PI 0.5) (angle pt1 pt2)))
     )
     (setq ptlist (list pt1)
           stang  (+ (* PI 0.5) (angle pt1 selpt))
     )
   )

   (setq endang (+ stang PI)
         nlen   (* (* _PLOTSCALE 0.15625) _SC) ;Controls the offset from the line
         lay    (dxf 8 data)
   )

   (if (or (= (dxf 0 data) "POLYLINE")
           (= (dxf 0 data) "LWPOLYLINE")
       )
     (setq val40 (cons 40 (dxf 40 data))
           val41 (cons 41 (dxf 41 data))
     )
     (setq val40 (cons 40 0.0)
           val41 (cons 41 0.0)
     )
   )
   (command "layer" "s" lay "")
   (foreach stpt ptlist
     (setq spt (polar stpt stang (* 0.5 nlen))
           ept (polar spt  endang nlen)
           plin  (list (cons 0 "POLYLINE")
                       val41
                       val40
                 )
           vtxt1  (list (cons 0 "VERTEX") (cons 10 spt) (cons 42 1.0))
           vtxt2  (list (cons 0 "VERTEX") (cons 10 stpt) (cons 42 -1.0))
           vtxt3  (list (cons 0 "VERTEX") (cons 10 ept))
           sqend  (list (cons 0 "SEQEND"))
     )
     (entmake plin)
     (entmake vtxt1)
     (entmake vtxt2)
     (entmake vtxt3)
     (entmake sqend)
   )
   (med_ret_ok)
   (princ)
)
(defun snut(/ pt1 pt pt2 pt3 pt4 pt5 pt6 pt7 pt8 en1 en2 en3 en4 en5 
              en6 apt ang ans size)
  (ltback nil)
  (setq size (getdist "\nSize of nut: "))
  (initget 1 "Top Side")
  (setq ans (getkword "\nTop view/Side view: "))
  (if (= ans "Side")
   (progn
    (setq pt (getpoint "\nStart point of nut: "))
    (setq apt (getpoint pt "\nDirection angle of nut: "))
    (setq ang (- (angle pt apt) 1.5708)
          pt1 (polar pt ang (* size 0.5))
          pt2 (polar pt (+ ang 3.14159) (* size 0.5))
          pt3 (polar pt1 ang (* size 0.5))
          pt4 (polar pt2 (+ ang 3.14159) (* size 0.5))
          pt5 (polar pt3 (+ ang 1.5708) size)
          pt6 (polar pt1 (+ ang 1.5708) size)
          pt7 (polar pt2 (+ ang 1.5708) size)
          pt8 (polar pt4 (+ ang 1.5708) size)
    )
    (command "line" pt1 pt6 "") (setq en1 (entlast))
    (command "line" "" pt5 "")  (setq en6 (entlast))
    (command "line" "" pt3 "")  (setq en2 (entlast))
    (command "line" "" pt4 pt8 "") (setq en4 (entlast))
    (command "line" "" pt7 "")  (setq en5 (entlast))
    (command "line" "" pt2 "")  (setq en3 (entlast))
    (command "fillet" "r" (* size 0.125) "fillet" en3 en5 "fillet" en1 en6
                                         "fillet" en6 en3 "fillet" en5 en1
    )
    (command "erase" en5 en6 "" "line" pt8 pt5 "")
    (setq en5 (entlast))
    (command "fillet" en4 en5 "fillet" en2 en5)
   )
   (progn 
    (setq pt (getpoint "\nCenter point of nut: "))
    (command "circle" pt "d" size "polygon" "6" pt "i" size)
    )
   )
)
;(defun c:lbk( / lay ent selpt data pt1 pt2 ptlist stang endang nlen
;                   val40 val41 stpt vtxt1 vtxt2 vtxt3 sqend)
;   (med_cur_set "C:LBK")
;   (setq ent    (entsel "\nSelect Line:")
;         selpt  (osnap (cadr ent) "END")
;         ent    (car ent)
;         data   (entget ent)
;         pt1    selpt
;   )
;   (setq ptlist (list pt1)
;           stang  (+ (* PI 0.5) (angle pt1 selpt))
;     )
;   )

;   (setq endang (+ stang PI)
;         nlen   (* 0.15625 _SC) ;Controls the offset from the line
;         lay    (dxf 8 data)
;   )

;   (if (or (= (dxf 0 data) "POLYLINE")
;           (= (dxf 0 data) "LWPOLYLINE")
;       )
;     (setq val40 (cons 40 (dxf 40 data))
;           val41 (cons 41 (dxf 41 data))
;     )
;     (setq val40 (cons 40 0.0)
;           val41 (cons 41 0.0)
;     )
;   )
;   (command "layer" "s" lay "")
;   (foreach stpt ptlist
;     (setq spt (polar stpt stang (* 0.5 nlen))
;           ept (polar spt  endang nlen)
;           plin  (list (cons 0 "POLYLINE")
;                       val41
;                       val40
;                 )
;           vtxt1  (list (cons 0 "VERTEX") (cons 10 spt) (cons 42 1.0))
;           vtxt2  (list (cons 0 "VERTEX") (cons 10 stpt) (cons 42 -1.0))
;           vtxt3  (list (cons 0 "VERTEX") (cons 10 ept))
;           sqend  (list (cons 0 "SEQEND"))
;     )
;     (entmake plin)
;     (entmake vtxt1)
;     (entmake vtxt2)
;     (entmake vtxt3)
;     (entmake sqend)
;   )
;   (med_ret_ok)
;   (princ)
;)


(defun c:lb (/ ang1 ang2 count ent num old pt1 pt2 pt3 pt4
               ss1 trl trl1 trl1data trldata)
   (med_cur_set "c:lb")
   (setvar "cmdecho" 0)
   (initget 1)
   (prompt "\nSelect entity not to be broken ")
   (setq trl (nentsel)
         trldata (entget (car trl))
   )
   (if (= (dxf 0 trldata) "VERTEX")
     (setq trl1 (entnext (car trl))
           trl1data (entget trl1)
	   pt1 (dxf 10 trldata)
	   pt2 (dxf 10 trl1data)
     )
     (setq pt2 (dxf 10 trldata)
           pt1 (dxf 11 trldata)
     )
   )
   (initget 1)
   (prompt "\nSelect entities to be broken ")
   (setq ss1 (ssget)
         num (sslength ss1)
         count 0
   )
    (if bkd
       (setq old bkd)
       (setq bkd (* _PLOTSCALE 0.04) old bkd)
    )       
    (setq bkd (getdist (strcat "\nBreak distance <" (rtos bkd 2 4) ">:")))
    (if (not bkd)
     (setq bkd old)
    )
    (while (< count num)
         (setq brent (ssname ss1 count)
	       brdata(entget brent))
         (if (= (dxf 0 brdata) "POLYLINE")
	     (pbreak brent)
	     (progn 
	       (setq pt3 (dxf 10 brdata)
                     pt4 (dxf 11 brdata)
                     ang1 (angle pt3 pt4)
                     ang2 (angle pt4 pt3)
                     brint (inters pt1 pt2 pt3 pt4)
                     br1 (polar brint ang1 bkd)
                     br2 (polar brint ang2 bkd)
                     ent (ssname ss1 count)
               )
               (command "break" ent br1 br2)
	     )
         )
	 (setq count (1+ count))
    )
    (med_ret_ok)
    (princ)	
) 

(defun pbreak (ent / ang1 ang2 cnt numb pt4 pt3 ptlist)
   (setq brent (entnext ent)
         brdata (entget brent)
   )
   (while (= (dxf 0 brdata) "VERTEX")
      (setq ptlist (append ptlist (list (dxf 10 brdata))))
      (setq brent (entnext brent)
            brdata (entget brent)
      )
   )
   (setq cnt 0
         numb (1- (length ptlist))
   )
   (while (< cnt numb)
      (setq pt3 (nth cnt ptlist)
            pt4 (nth (1+ cnt) ptlist)
	    ang1 (angle pt3 pt4)
	    ang2 (angle pt4 pt3)
	    brint (inters pt1 pt2 pt3 pt4)
      )
      (if brint
        (progn
	 (setq br1 (polar brint ang1 bkd)
	       br2 (polar brint ang2 bkd)
	 )
	 (command "break" ent br1 br2)
	 (setq ent (entlast))
	)
      )
      (setq cnt (1+ cnt))
   )
   (setq ptlist nil
         brint nil
   )
)
(defun entlist ()
    (setq ename (ssname ss1 count)
          edata (entget ename)
    )
)
(defun c:fl ( / ss1 edata ename count num lname coff)
    (prompt "\nSelect entities upon layers to be frozen: ")
    (setvar "cmdecho" 0)
    (setq flss (ssget)
          num  (sslength flss)
	  count 0
    )
    (while (< count num)
         (setq ename (ssname flss count)
	       edata (entget ename)
	 )
         (set (read (strcat "lname" (itoa count))) (cdr (assoc 8 edata)))
         (setq count (1+ count))
    )
    (setq count 0)
    (command "layer")
    (while (< count num)
         (setq lname (eval (read (strcat "lname" (itoa count)))))
         (if (/= lname (getvar "CLAYER"))
              (command "f" lname)
              (setq coff (strcat "Did not turn off curent layer " lname))
         )
         (setq count (1+ count))
    )
    (command "")
    (if coff
         (progn
              (princ)
              (prompt coff)
              (princ)
    )    )
(princ)
)


(defun c:lisp( / rout)
   (setq rout (getstring "\nName of lisp file to load: "))
   (if (findfile (strcat rout ".lsp"))
       (load rout)
       (progn (terpri) (prompt "File name not found."))
   )
)




(defun c:bn( / bnent bndata bname)
   (setq bnent (car (entsel))
         bndata(entget bnent)
   )
   (if (= (dxf 0 bndata) "INSERT")
     (progn
       (setq bname (dxf 2 bndata))
       (prompt (strcat "\nBlock name is " bname "!"))
     )
     (prompt "\nEntity Selected is not a block.")
   )
   (princ)
)
(defun c:cl( / clss cllen clcnt clnew clent cldata cllay nwlay)
   (med_cur_set "C:CL")
   (prompt "\nSelect entities to be changed to selected layer: ")
   (setq clss (ssget)
         cllen(sslength clss)
         clcnt 0
   )
   (while (not (setq clnew (entsel "\nSelect Entity of desired layer: "))))
   (setq clnew (car clnew)
         clnew (dxf 8 (entget clnew))
   
   )
   (while (< clcnt cllen)
     (setq clent (ssname clss clcnt)
           cldata(entget clent)
           cllay (assoc 8 cldata)
           nwlay (cons 8 clnew)
           cldata(subst nwlay cllay cldata)
           clcnt (1+ clcnt)
     )
     (entmod cldata)
   )
   (prompt (strcat "\nEntities have been move to the " clnew " layer."))
   (med_ret_ok)
   (princ)
)

(defun c:em( / emss1 emss2 emlen emcnt empt )
  (prompt "\nSelect Boundries to extend to:")     
  (setq emss1 (ssget))
  (prompt "Select entities to be extended: ")
  (setq emss2 (ssget)
        emlen (sslength emss2)
        emcnt 0
        empt  (getpoint "\nSelect point to base extension: ")
  )
  (command "extend" emss1 "")
  (while (< emcnt emlen)
    (setq ement (ssname emss2 emcnt)
          ement (list ement empt)
          emcnt (1+ emcnt)
    )
    (command ement)
  )
  (command "")
  (princ)
)
(defun c:lt( / ltss ltnew ltnewlay ltlaydata ltewen)
   (med_cur_set "C:LT")
   (prompt "\nSelect entities to be changed to selected entity's linetype: ")
   (setq ltss (ssget))
   (while (not (setq ltnewen (entsel "\nSelect Entity of desired linetype: "))))
   (setq ltnewen (car ltnewen)
         ltnew   (dxf 6 (entget ltnewen))
   )
   (if (not ltnew)
     (progn
       (setq ltnewlay (dxf 8 (entget ltnewen))
             ltlaydata(tblsearch "LAYER" ltnewlay)
             ltnew (dxf 6 ltlaydata)
       )
       (setq ltans (getstring "\nSet linetypes to bylayer Yes/<No>:"))
       (if (not (or (= ltans "") (not (= (strcase ltans) "Y"))))
          (setq ltnew "Bylayer")
       )
     )
   )
   (command "change" ltss "" "P" "lt" ltnew "")
   (prompt (strcat "\nEntities have been changed to the " ltnew " linetype."))
   (med_ret_ok)
   (princ)
)

(defun c:plmake()
   (prompt "\nSelect lines to be changed to polylines: ")
   (setq ss1 (ssget)
         count 0
         num (sslength ss1)
   )
   (while (< count num)
          (setq en (ssname ss1 count)
                endt (entget en))
          (if (= (dxf 0 endt) "LINE")
                (command "pedit" en "y" "")
          )
          (setq count (1+ count))
    )
    (prompt "\nAll lines converted.")
    (princ)
)
(defun c:pw()
  (c:plwide)
)
(defun c:plwide( / pwss nwth pwcnt pwlcnt pwnum pwent oldval swth ewth)
   (med_cur_set "C:PLWIDE")
   (princ "\nSelect polylines for width change: ")
   (setq pwss (ssget))
   (if pwss
      (progn
       (setq pwent (car (entsel "\nSelect PLINE with width to match: ")))
       (if pwent
         (progn
          (setq pwdata(entget pwent))
          (if (or (= (dxf 0 pwdata) "POLYLINE") (= (dxf 0 pwdata) "LWPOLYLINE"))
             (setq nwth (dxf 40 pwdata))
             (setq nwth 0.0)
          )
         )
         (progn
           (setq nwth (getdist "\nNew width for selected polylines: "))
         )
       )
       (setq pwcnt 0)
       (setq pwlcnt 0)
       (setq pwnum (sslength pwss))
       (While (< pwcnt pwnum)
            (if (OR (= "POLYLINE" (dxf 0 (setq pwent (entget (ssname pwss pwcnt)))))
                (= "LINE" (dxf 0 pwent) ) (= (dxf 0 pwent) "ARC")
		(= (dxf 0 pwent) "LWPOLYLINE")   )
                (progn
                 (if (or (= (dxf 0 pwent) "LINE") (= (dxf 0 pwent) "ARC"))
                   (progn
                     (command "pedit" (dxf -1 pwent) "y" "w" nwth "")
   	                (setq pwent (entget (entlast)))
                   )
		   (progn
                     (command "pedit" (dxf -1 pwent) "w" nwth "")
   	                (setq pwent (entget (entlast)))
                   )
                 )
                 ;(setq swth (cdr (setq oldval (assoc 40 pwent))))
                 ;(setq swth nwth)
                 ;(setq pwent (subst (cons 40 swth) oldval pwent))
                 ;(setq ewth (cdr (setq oldval (assoc 41 pwent))))
                 ;(setq ewth nwth)
                 ;(setq pwent (subst (cons 41 ewth) oldval pwent))
                 ;(entmod pwent)
                 ;(setq plent (entnext (dxf -1 pwent))
                 ;      pldata (entget plent)
                 ;)
                 ;(while (/= (dxf 0 pldata) "SEQEND")
                 ;   (setq oldwdth (assoc 40 pldata)
                 ;         newwdth (cons 40 swth)
                 ;         pldata (subst newwdth oldwdth pldata)
                 ;         pldata (entmod pldata)
                 ;         oldwdth (assoc 41 pldata)
                 ;         newwdth (cons 41 swth)
                 ;         pldata (subst newwdth oldwdth pldata)
                 ;         pldata (entmod pldata)
                 ;         plent (entnext plent)
                 ;         pldata (entget plent)
                 ;   )
                 ;)
                 ;(entupd (dxf -1 pwent))
                 (setq pwlcnt (1+ pwlcnt))


                )
            )
            (setq pwcnt (1+ pwcnt))
      )
     )
   )
   (princ "Changed ")
   (princ pwlcnt)
   (princ " PLine widths.")
   (med_ret_ok)
   (terpri)
)
(defun c:pbox (/ pt1 pt2 ptlist)
     (setq pt1  (getpoint "\nFirst corner: ")
           pt2  (getcorner pt1 "\nSecond corner: ")
           ptlist (list pt1 
                        (list (car pt1) (cadr pt2))
                        pt2
                        (list (car pt2) (cadr pt1))
                  )
     )
     (pmake ptlist T)
     (princ)

)

;(defun pmake ( ptlist plclose / );plin vtxt sqend)
;(setq tmpforme ptlist)
;  (if plclose
;     (setq plin  '((0 . "POLYLINE") (70 . 1)))
;     (setq plin  '((0 . "POLYLINE")))
;  )
;  (setq vtxt   (list (cons 0 "VERTEX"))
;        sqend  (list (cons 0 "SEQEND"))
;  )
;  (if CR_LAYER
;   (progn
;     (setq plin (append plin (list (cons 8 CR_LAYER)))
;           vtxt (append vtxt (list (cons 8 CR_LAYER)))
;           sqend (append sqend (list (cons 8 CR_LAYER)))
;     )
;   )
;  )
;
;  (entmake plin)
;  (foreach pt ptlist
;     (setq vertx (cons 10 pt)
;           vertx (append vtxt (list vertx))
;     )
;     (entmake vertx)
;  )
;  (entmake sqend)
;
;  (setq CR_LAYER nil)
;)   

(defun c:sl ()
   (while (not (setq slen (entsel "\nSelect entity to set new layer: "))))
   (setq sldata (entget (car slen))
         sllay  (dxf 8 sldata)
   )
   (command "layer" "s" sllay "")
   (prompt (strcat "\nCurrent layer is now " sllay "."))
   (princ)
)

(defun c:tm ( / tmss1 tmss2 tmlen tmcnt tmpt tment)
  (prompt "Select edges: ")
  (setq tmss1 (ssget))
  (prompt "Select objects to be trimed: ")
  (setq  tmss2 (ssget)
         tmlen (sslength tmss2)
         tmcnt 0
         tmpt (getpoint "\nSelect point to base trim: ")
  )
  (command "trim" tmss1 "")
  (while (< tmcnt tmlen)
    (setq tment (ssname tmss2 tmcnt)
          tment (list tment tmpt)
          tmcnt (1+ tmcnt)
    )
    (command tment)
  )
  (command "")
  (princ)
)



(defun c:bldstl( / _stylenms stdata curcmdlst curalilst fname fn)
   (setq _stylenms (list (dxf 2 (tblnext "style" T))))
   (while (setq stdata (tblnext "style"))
     (setq _stylenms (append _stylenms (list (dxf 2 stdata))))
   )
   (setq curcmdlst (atoms-family 1)
         curalilst (getalias)
   )
   (setq fname (strcat (getvar "MYDOCUMENTSPREFIX") "\\MEDlsp.tmp"))
   (setq fn (open fname "w"))
   (write-line ";Moore Design Temporary lisp file for style command creation" fn)
   (close fn)
   (setq fn (open fname "a"))
   (foreach sty _stylenms
     (if (not (or (member (strcat "C:" sty) curcmdlst)
                  (member sty curalilst)
                  (> (length (mparse sty " " nil nil)) 1)
         )    )
       (progn
         (write-line (strcat "(defun c:" sty "()") fn)
         (write-line "(smlayer _MEDTEXT)" fn)
         (write-line (strcat "(command \"dtext\" \"s\" \"" sty "\")") fn)
         (write-line ")" fn)
       )
     )
   )
   (close fn)
   (load (strcat (getvar "MYDOCUMENTSPREFIX") "\\MEDlsp.tmp"))
)

(defun getalias (/ al_err al_oe s al_oce aliasi lineno first line lfile)

  (setq fname  (findfile "acad.pgp")
        aliasi (open fname "r")
        aliaslist nil
  )

  (if aliasi
    (progn
      (setq lineno 0
            first T
      )
      (while (setq line (read-line aliasi))
        ;; Check each line for leading semi-colon
        (if (and (/= (substr line 1 1) ";")     ; Leading semi-colon?
                 (/= (substr line 1 1) "")      ; Blank line?
                 (/= (substr line 1 1) "\n"))   ; Carriage return?
         (progn 
          (setq j      0
                al_str "" 
                c_str  ""
          )
          (while (/= (setq tmpstr (substr line (setq j (1+ j)) 1)) ",")
            (if (/= tmpstr " ")
              (setq al_str (strcat al_str tmpstr))
            )
          )
          (while (and (/= (setq tmpstr (substr line (setq j (1+ j)) 1)) "")
                      (/= tmpstr ";") 
                      (/= tmpstr ",")
                      (/= tmpstr "\n")
                 )
            (if (and (/= tmpstr " ") (/= tmpstr "*") (/= tmpstr "\t"))
              (setq c_str (strcat c_str tmpstr))
            )

          )
          (setq aliaslist (append aliaslist (list al_str)))
         )
        )
      )
    )
    ;; else
    (progn
      (princ "\nCouldn't find or read the file \"acad.pgp\". ")
    )
  )
  (setq aliasi (close aliasi))
  aliaslist
)

(defun linemake ( linept1 linept2 linelay / )
  (if (not linelay)
    (setq linelay (getvar "CLAYER"))
  )
  (setq linedat(list (cons 0 "LINE")
                     (cons 10 linept1) 
                     (cons 11 linept2)
                     (cons 8 linelay)
               )
  )
  (entmake linedat)
)   

(defun c:il()
  (setq ent (entsel "\nSelect Entity to Isolate Layer: "))
  (if ent
    (progn
      (setq ent (car ent)
            data(entget ent)
            laynam (dxf 8 data)
            _LAYLIST nil
      )
      (setq lay (tblnext "LAYER" T))
      (while lay
        (setq lnm (dxf 2 lay))
        (if (> (dxf 62 lay) 0)
           (setq _LAYLIST (append _LAYLIST (list lnm)))
        )
        (setq lay (tblnext "LAYER"))
      )
      (smlayer (list laynam nil nil))
      (command "layer" "off" "*" "" "")
    )
  )

)
(defun c:uil()
  (if _LAYLIST
     (progn
       (foreach lay _LAYLIST
          (command "layer" "on" lay "")
       )
     )
  )
  (setq _LAYLIST nil)
)

(defun c:blkreins()
  (if _BLKREINS
      (setq blknm _BLKREINS
	    _BLKREINS nil
      )
      (setq blknm (getstring "\nBlock Name to re-insert: "))
  )
  (setq cmdstat (getvar "cmdecho"))
  (setvar "cmdecho" 0)
  (if blknm
     (progn
        (setq blkss (ssget "x" (list (cons 0 "INSERT")
                                     (cons 2 blknm)
                               )     
                    )
        )
     )
  )
  (if blkss
   (progn
    (setq blklen (sslength blkss)
          blkcnt 0
    )
    (command "insert" (strcat blknm "=") nil)
    (while (< blkcnt blklen)
      (setq blkent (ssname blkss blkcnt)
            blkdata(entget blkent (list "*"))
            blk_hd blkent
            blkins (dxf 10 blkdata)
            blklay (dxf 8  blkdata)
            blkrot (dxf 50 blkdata)
            blksc  (dxf 41 blkdata)
            blkatts nil
            blkxdata (assoc -3 blkdata)
            blkcnt (1+ blkcnt)
      )
      (if (= (dxf 66 blkdata) 1)
         (progn
          (while (/= (dxf 0 blkdata) "SEQEND")
            (setq blkent (entnext blkent)
                  blkdata(entget blkent)
            )
            (setq attval (list (dxf 2 blkdata) (dxf 1 blkdata)
                               (dxf 50 blkdata) (dxf 10 blkdata)
                         )
                  blkatts (append blkatts (list attval))
            )
          )
         )
      )
      (command "layer" "t" blklay "s" blklay "")
      (setq oldreq (getvar "attreq"))
      (setvar "attreq" 0)
      (entdel blk_hd)
      (if _BLKOFFSET
        (setq blkins (polar blkins 0.0 (nth 0 _BLKOFFSET))
              blkins (polar blkins (* PI 0.5) (nth 1 _BLKOFFSET))
        )
      )
      (command "insert" blknm blkins blksc "" (angtos blkrot))
      (setq newblk (entlast)
            newent newblk
            newdata(entget newblk)
            newatts nil
      )
      (if blkxdata
        (setq newdata(append newdata (list blkxdata)))
      )
      (entmod newdata)
      (if (= (dxf 66 newdata) 1)
         (progn
          (while (/= (dxf 0 newdata) "SEQEND")
            (setq newent (entnext newent)
                  newdata(entget newent)
            )
            (setq atttag (dxf 2 newdata))
            (if (setq attitem (assoc atttag blkatts))
               (progn
                 (setq oldval (assoc 1 newdata)
                       newval (cons 1 (nth 1 attitem))
                       newdata(subst newval oldval newdata)
                      ; oldval (assoc 10 newdata)
                      ; newval (cons 10 (nth 3 attitem))
                      ; newdata(subst newval oldval newdata)
                       oldval (assoc 50 newdata)
                       newval (cons 50 (nth 2 attitem))
                       newdata(subst newval oldval newdata)
                 )
                 (entmod newdata)
               )
            )
          )
         )
      )
      (entupd newblk)
    )
   )
  )
  (setvar "attreq" oldreq)
  (setvar "cmdecho" cmdstat)
)

(defun c:linkprefix()
	(setq PrefixEnt (nentsel "\nSelect Prefix Text Entity: "))
	(if PrefixEnt
		(progn
			(prompt "\nSelect Text Entities to Prefix (Chars replaced will match the prefix selected):")
			(setq PrefixData (entget (car prefixent))
				  PrefixOID (vla-get-objectid (vlax-ename->vla-object (dxf -1 prefixdata)))
				  prefixvalue (strcat "%<\\AcObjProp Object(%<\\_ObjId " (itoa PrefixOID) ">%).TextString \\f \"%tc1\">%")
				  prefixtext (dxf 1 prefixdata)
				  prefixlength (strlen prefixtext)
				  textss (ssget)
			)
			(if textss
				(progn
					(setq cnt 0
						  textsslen (sslength textss)
					)
					(while (< cnt textsslen)
						(setq textdata (entget (ssname textss cnt))
							  cnt (1+ cnt)
						)
						(if (= (dxf 0 textdata) "TEXT")
							(progn
								(setq txtvalue (dxf 1 textdata))
								(if (> (strlen txtvalue) prefixlength)
									(setq newvalue (strcat prefixvalue (substr txtvalue (+ prefixlength 1))))
									(setq newvalue (strcat prefixvalue txtvalue))
								)
								(setq newentdata (subst (cons 1 newvalue) (assoc 1 textdata) textdata))
								(entmod newentdata)
							)
						)
					)
				)
			)
		)
	)
	(princ prefixvalue)
	(princ)
)

(defun c:linkprefixAtt()
	(setq PrefixEnt (nentsel "\nSelect Prefix Text Entity: "))
	(if PrefixEnt
		(progn
			(prompt "\nSelect Text Entities to Prefix (Chars replaced will match the prefix selected):")
			(setq PrefixData (entget (car prefixent))
				  PrefixOID (vla-get-objectid (vlax-ename->vla-object (dxf -1 prefixdata)))
				  prefixvalue (strcat "%<\\AcObjProp Object(%<\\_ObjId " (itoa PrefixOID) ">%).TextString \\f \"%tc1\">%")
				  prefixtext (dxf 1 prefixdata)
				  prefixlength (strlen prefixtext)
			)
			(while (setq textent (nentsel "\nSelect Attribute: "))
				(setq textdata (entget (car textent)))
				(if (= (dxf 0 textdata) "ATTRIB")
					(progn
						(setq txtvalue (dxf 1 textdata))
						(if (> (strlen txtvalue) prefixlength)
							(setq newvalue (strcat prefixvalue (substr txtvalue (+ prefixlength 1))))
							(setq newvalue (strcat prefixvalue txtvalue))
						)
						(setq newentdata (subst (cons 1 newvalue) (assoc 1 textdata) textdata))
						(entmod newentdata)
						(entupd (dxf 330 newentdata))
					)
				)
			)
		)
	)
	(princ prefixvalue)
	(princ)
)
(defun c:linkvalue()
	(setq PrefixEnt (nentsel "\nSelect Source Text/Atribute Entity: "))
	(if PrefixEnt
		(progn
			(prompt "\nSelect Text/Attribute Entities Link")
			(setq PrefixData (entget (car prefixent))
				  PrefixOID (vla-get-objectid (vlax-ename->vla-object (dxf -1 prefixdata)))
				  prefixvalue (strcat "%<\\AcObjProp Object(%<\\_ObjId " (itoa PrefixOID) ">%).TextString \\f \"%tc1\">%")
				  prefixtext (dxf 1 prefixdata)
				  prefixlength (strlen prefixtext)
			)
			(while (setq textent (nentsel "\nSelect Text/Attribute: "))
				(setq textdata (entget (car textent)))
				(if (or (= (dxf 0 textdata) "ATTRIB")
						(= (dxf 0 textdata) "TEXT")
					)
					(progn
						(setq newvalue prefixvalue
						      newentdata (subst (cons 1 newvalue) (assoc 1 textdata) textdata)
						)
						(entmod newentdata)
						(if (= (dxf 0 textdata) "TEXT")
							(entupd (dxf 330 newentdata))
						)
					)
				)
			)
		)
	)
	(princ prefixvalue)
	(princ)
)

;;;This one builds a string of linked data for the Target Text/attribute to receive.
(defun c:setlink()
	(setq LinkEnt (nentsel "\nSelect Item to recieve Link data: "))
	(if LinkEnt
		(progn
			(command "undo" "m")
			(prompt "\nSelect Text/Attribute Entities Link to:")
			(setq LinkValue "")
			(while (setq textent (nentsel "\nSelect Text/Attribute: "))
				(setq linkedentdata (entget (car textent))
					  linkedentOID (vla-get-objectid (vlax-ename->vla-object (dxf -1 linkedentdata)))
				)
				(if (= LinkValue "")
					(setq LinkValue (strcat "%<\\AcObjProp Object(%<\\_ObjId "  (itoa linkedentOID) ">%).TextString \\f \"%tc1\">%"))
					(setq LinkValue (strcat LinkValue "-" "%<\\AcObjProp Object(%<\\_ObjId "  (itoa linkedentOID) ">%).TextString \\f \"%tc1\">%"))
				)
			)
			(setq LinkEntData (entget (car LinkEnt)))
			(if (or (= (dxf 0 LinkEntData) "ATTRIB")
					(= (dxf 0 LinkEntData) "TEXT")
			)
				(progn
					(setq newvalue LinkValue
						  newentdata (subst (cons 1 newvalue) (assoc 1 LinkEntData) LinkEntData)
					)
					(entmod newentdata)
					(if (= (dxf 0 LinkEntData) "TEXT")
						(entupd (dxf 330 newentdata))
					)
				)
			)
		)
		(princ "\nNothing Selected:")	
	)
	(princ)
)


(defun c:setlinksum()
	(setq LinkEnt (nentsel "\nSelect Item to recieve Link data: "))
	(if LinkEnt
		(progn
			(command "undo" "m")
			(prompt "\nSelect Text/Attribute Entities Link to:")
			(setq LinkValue "")
			(while (setq textent (nentsel "\nSelect Text/Attribute: "))
				(setq linkedentdata (entget (car textent))
					  linkedentOID (vla-get-objectid (vlax-ename->vla-object (dxf -1 linkedentdata)))
				)
				(if (= LinkValue "")
					(setq LinkValue (strcat "%<\\AcExpr (%<\\AcObjProp Object(%<\\_ObjId "  (itoa linkedentOID) ">%).TextString>%"))
					(setq LinkValue (strcat LinkValue "+" "%<\\AcObjProp Object(%<\\_ObjId "  (itoa linkedentOID) ">%).TextString>%"))
				)
			)
			(setq LinkEntData (entget (car LinkEnt)))
			(if (or (= (dxf 0 LinkEntData) "ATTRIB")
					(= (dxf 0 LinkEntData) "TEXT")
			)
				(progn
					(setq newvalue (strcat LinkValue ")>%")
						  newentdata (subst (cons 1 newvalue) (assoc 1 LinkEntData) LinkEntData)
					)
					(entmod newentdata)
					(if (= (dxf 0 LinkEntData) "TEXT")
						(entupd (dxf 330 newentdata))
					)
				)
			)
		)
		(princ "\nNothing Selected:")	
	)
	(princ)
)

(defun c:showfieldcode()
	(setq ent (nentsel "\nSelect Entity to show field code"))
	(if ent
		(progn
			(setq entdata (entget (car ent)))
			(if (or (= (dxf 0 entdata) "TEXT") (= (dxf 0 entdata) "MTEXT") (= (dxf 0 "ATTRIB")))
				(progn
					(setq obj (vlax-ename->vla-object (dxf -1 entdata))
						  fieldcode (vla-fieldcode obj)
					)
					(princ "\n")
					(princ fieldcode)
				)
			)
		)
	)
)


(princ "Done.")
