(princ "\rLoading MEDDatabase...")
(defun MEDUserStatus ()
	(setq CheckUserStatement (strcat "Select * from MEDUsers WHERE UserName='" (getvar "LOGINNAME") "'")
		  CheckUserResults (MEDProcessSQLStatement CheckUserStatement)
	)
	(if (and CheckUserResults (> (length CheckUserResults) 1))
		(setq _MEDAdministrativeUser T)
		(setq _MEDAdministrativeUser nil)
	)
)
(defun MED-DotNet-Ready ( )
	(member (type processsqlstatementNET) '(EXRXSUBR SUBR USUBR EXSUBR))
)
(defun MED-EnsureDotNet ( / p err )
	(if (not (MED-DotNet-Ready))
		(if (setq p (findfile "MED-DotNet.dll"))
			(progn
				(setq err (vl-catch-all-apply 'command-s (list "_.NETLOAD" p)))
				(if (vl-catch-all-error-p err)
					(vl-catch-all-apply 'vl-cmdf (list "_.NETLOAD" p))
				)
			)
		)
	)
	(MED-DotNet-Ready)
)
(defun MEDProcessSQLStatement (SQLStatementToProcess)
	;(processsqlstatementLISP sqlstatementtoprocess)
	(if (not (MED-EnsureDotNet))
		(progn
			(princ "\nMEDProcessSQLStatement: ProcessSQLStatementNET is not loaded.")
			nil
		)
		(processsqlstatementNET sqlstatementtoprocess)
	)
)

(defun ProcessSQLStatement (SQLStatementToProcess)
	(MEDProcessSQLStatement SQLStatementToProcess)
)

(defun med_getdesc (AppType LookupCode)
	(setq mgd-sqlstatement (strcat "Select ITEMDESC From MEDType Where ITEMTYPE='" AppType "' and ITEMCODE=" (itoa lookupcode))
		  mgd-resultset (MEDProcessSQLStatement mgd-sqlstatement)
	)
	(if (and mgd-resultset (= (length mgd-resultset) 2))
		(setq mgd-returndata (car (cadr mgd-resultset)))
		(setq mgd-returndata "*************INVALID DATABASE ENTRY***************")
	)
	mgd-returndata
)
(defun bld_data_list (bdl_medtype)
	(setq bdl_SQLStatement (strcat "Select ITEMDESC, ITEMCODE from MEDTYpe Where ITEMTYPE = '" bdl_medtype "'")
		  bdl_datalist (cdr (MEDProcessSQLStatement bdl_SQLStatement))
		  bdl_returnlist (list)
	)
	(if bdl_datalist
		(foreach item bdl_datalist
			(setq bdl_returnlist (append bdl_returnlist (list (car item) (fix (cadr item)))))
		)
	)
	bdl_returnlist
)
(if (MED-DotNet-Ready)
	(MEDUserStatus)
	(progn
		(princ "\nMED-DotNet not ready yet; admin check deferred until NETLOAD finishes.")
		(setq _MEDAdministrativeUser nil)
	)
)
(princ "Done.")
