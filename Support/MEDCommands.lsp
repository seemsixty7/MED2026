(princ "\rLoading MEDCommand...")
(defun C:LoadLayers( / Laylist)
	(setq Laylist (cdr (ProcessSQLStatement "Select * From Layers")))
	(foreach Layer Laylist
		(medmakelayer (cdr layer))
	)
	(princ)
)

(setq MEDListAppDataFormat
	(list (list "MED_FITTING" (list (list "Tag" 0) (list "Size" 1) (list "Code" 2) (list "Desc" nil) (list "Alt" 3) (list "Depth" 4)(list "Flange" 5)))
		  (list "MED_CONDUIT" (list (list "Tag" 0) (list "Size" 1) (list "Code" 2) (list "Desc" nil) (list "Dist" 3) (list "Mesr" 4)))
		  (list "MED_CABLE"   (list (list "Tag" 0) (list "Size" 1) (list "Code" 2) (list "Desc" nil) (list "RTag" 3) (list "Dist" 4) (list "Mesr" 5)))
		  (list "MED_TRAY"    (list (list "Tag" 0) (list "Size" 1) (list "Code" 2) (list "Desc" nil) (list "Dist" 3) (list "Depth" 4) (list "Mesr" 5) (list "Flange" 6)))
		  (list "MED_EQUIP"   (list (list "Tag" 0) (list "Code" 1) (list "Desc" nil)))
	)
)

(defun c:MEDlist( / medent)
 (med_cur_set "c:MEDlist")
 (while (not medent)
   (setq medent (car (entsel "\nSelect Entity to list: ")))
 )
 (setq applist (xd_apps medent)
       numapps (length applist)
       appcnt  0
 )
 (prompt "\n\n")
 (textscr)
 (while (< appcnt numapps)
   (setq appnm (nth appcnt applist)
         appdata (cdr (xdataget medent appnm))
         datalen (length appdata)
         applen  (eval (read (strcat "len" (substr appnm 4))))
         numtags (/ datalen applen)
         tagcnt 0
   )
   (while (< tagcnt numtags)
   	 (setq printdata (ShowMEDListData appnm tagcnt appdata medent))
   	 (foreach stringtoprint printdata
   	 	 (princ stringtoprint)
   	 )
     (setq tagcnt (1+ tagcnt))
     (getstring "\n\nPress Return to Continue")
   )
   (setq appcnt (1+ appcnt))
 )
 (med_ret_ok)
 (princ)
)
(defun ShowMEDListData (MEDAppName TagCount MEDAppData MEDEntity / 
		smld-count smld-printlist smld-applen smld-datacnt smld-code smld-mesr smld-length)
	(setq smld-printlist (list)
		  smld-applen (eval (read (strcat "len" (substr MEDAppName 4))))
		  smld-DataCnt (1- smld-applen)
	)
	(foreach MEDListItem (cadr (assoc MEDAppName MEDListAppDataFormat))
		(setq smld-count (cadr MedListItem))
	    (if smld-count
	    	(setq smld-item (nth (+ smld-count (*  smld-applen TagCount)) MEDAppData))
	    )
		(setq smld-itemstring (car MEDListItem))
		(cond
			((= smld-itemstring "Tag")
				(setq smld-printlist (append smld-printlist (list (strcat "\n" MEDAppName " | " smld-item))))
			)
			((= smld-itemstring "Size")
				(setq smld-printlist (append smld-printlist (list (strcat "\n--->Size  = " (rtos smld-item 2 8))))
					  smld-size smld-item
				)
			)
			((= smld-itemstring "Code")
				(setq smld-printlist (append smld-printlist (list (strcat "\n--->Code  = " (itoa smld-item))))
					  smld-code smld-item
				)
			)
			((= smld-itemstring "Desc")
				(setq smld-printlist (append smld-printlist (list (strcat "\n--->Desc  = " (clookup smld-code smld-size MEDAppName)))))
			)
			((= smld-itemstring "Alt")
				(setq smld-printlist (append smld-printlist (list (strcat "\n--->Alt   = " (rtos smld-item 2 4)))))
			)
			((= smld-itemstring "Depth")
				(setq smld-printlist (append smld-printlist (list (strcat "\n--->Depth = " (rtos smld-item 2 4)))))
			)
			((= smld-itemstring "Dist")
				(if (= MEDAppName _TRAY)
					(setq smld-mesr (nth (1- (+ smld-datacnt (*  smld-applen TagCnt))) MEDAppData))
					(setq smld-mesr (nth (+ smld-datacnt (*  smld-applen TagCnt)) MEDAppData))
				)
				(if (= smld-mesr "T")
					(setq smld-length (polylen MEDEntity)
						  smld-printlist (append smld-printlist (list (strcat "\n--->Dist  = " (rtos smld-length) " (Calculated)")))
					)
					(setq smld-printlist (append smld-printlist (list (strcat "\n--->Dist  = " (rtos smld-item) " (Stored)"))))
				)
			)
			((= smld-itemstring "Mesr")
				(setq smld-printlist (append smld-printlist (list (strcat "\n--->Mesr  = " smld-item))))
			)
			((= smld-itemstring "RTag")
				(setq smld-printlist (append smld-printlist (list (strcat "\n--->RTag  = " smld-item))))
			)
			((= smld-itemstring "Flange")
				(setq smld-printlist (append smld-printlist (list (strcat "\n--->Flange= " (rtos smld-item 2 2)))))
			)
			
		)
	)
	smld-printlist
)

(defun med_text (txt_specifier txt_startpoint)
                                        ;txt_specifier is the reference found int the spec file as in "T1" or "T2"
                                        ;txt_startpoint is a startpoint, rotation for the text, and justification ((0.0 0.0 0.0) 0.0 "L")
   (setq layerdata _MEDTEXT)
   (setq txtstydata (assoc txt_specifier MED_TXT_STYLE_MAP)
         txtstylnm  (cadr txtstydata)
         txtstyleheight (nth 3 txtstydata)
   )
   (if layerdata
      (progn
         (if (= (length txtstydata) 11)
            (setq newlayname (if (= (nth 1 (nth 9 txtstydata)) 0)
            		       		(strcat (nth 0 (nth 9 txtstydata)) (nth 0 layerdata))
            		       		(strcat (nth 0 layerdata) (nth 0 (nth 9 txtstydata)))
            		       	)
                  oldlayname (nth 0 layerdata)
                  layerdata  (subst newlayname oldlayname layerdata)
                  newlaycol  (nth 10 txtstydata)
                  oldlaycol  (nth 1 layerdata)
                  layerdata  (subst newlaycol oldlaycol layerdata)
            )
         )
         (smlayer layerdata)
      )
      (prompt "\n*********Layer Info Not Found Using Current Layer")
   )
   (if (not (tblsearch "style" txtstylnm))
      (MEDMakeTextStyle txtstydata)
   )
   (if (= (getvar "TILEMODE") 1)
   	   (MEDSetTextStyleHeight txtstylnm (* _SC _PLOTSCALE txtstyleheight))
   	   (MEDSetTextStyleHeight txtstylnm (* _PLOTSCALE txtstyleheight))
   )
   (if txt_startpoint
      (command "dtext"
               "s"
               txtstylnm
               "j"
               (nth 2 txt_startpoint)
               (nth 0 txt_startpoint)
               (nth 1 txt_startpoint)
      )
      (command "dtext" "s" txtstylnm)
   )
)

(defun c:alead()
	(medleader nil T 1.0 nil)
)

(defun c:glead()
	(medleader "grabit" T 0.5 nil)
)
(defun c:grab()
	(medleader "grabit" T 0.5 nil)
)

(defun c:al()
   (medleader nil nil 1.0 nil)
)

(defun c:gl()
   (medleader "grabit" nil 0.5 nil)
)

(defun c:T1 ()
   (med_text "T1" nil)
)
(defun c:T2 ()
   (med_text "T2" nil)
)
(defun c:T3 ()
   (med_text "T3" nil)
)
(defun c:B1 ()
   (med_text "B1" nil)
)
(defun c:B2 ()
   (med_text "B2" nil)
)
(defun c:B3 ()
   (med_text "B3" nil)
)

(defun c:cd (/ ex len y1 y2 x1 x2 dirxy coor cord coord inspt rot part1
               part2 sub trl usepoint1 usepoint2)
   (setvar "cmdecho" 0)
   (setq ex nil
         len 1
         orgosmode (getvar "OSMODE")
   )
   (setvar "OSMODE" 0)
   (prompt "\nSelect coordinate line:[Press Enter to Pick two Points] ")
   (setq trl (entsel))
   (if trl
       (setq usepoint1 (osnap (cadr trl) "endp")
       	     usepoint2 (osnap (cadr trl) "midp")
       	     y1 (cadr usepoint1)
             y2 (cadr usepoint2)
             x1 (car usepoint1)
             x2 (car usepoint2)
             ex T
       )
       (progn
		   (setq usepoint1 (getpoint "\nSelect Point: "))
		   (if usepoint1
			   (progn
				   (setq orgorthomode (getvar "ORTHOMODE"))
				   (setvar "ORTHOMODE" 1)
				   (setq usepoint2 (getpoint usepoint1 "\nSelect otherpoint"))
				   (setvar "ORTHOMODE" orgorthomode)
				   (if usepoint2
					   (setq ex T)
					   (princ "\nInvalid Point")
				   )
				)
				(princ "\nInvalid Point")
			)
	  )
    )
    (if ex
    	(progn
    		(setq test1 usepoint1 test2 usepoint2)
			(setq y1 (cadr usepoint1)
				  y2 (cadr usepoint2)
				  x1 (car usepoint1)
				  x2 (car usepoint2)
			)
           (cond 
           	   ((and (< y1 0)(equal y1 y2 0.001))
           	   	   (setq dirxy "S")
           	   	   (setq coor (cadr (trans usepoint1 0 1)))
           	   )
           	   ((and (< x1 0)(equal x1 x2 0.001))
           	   	   (setq dirxy "W")
           	   	   (setq coor (car (trans usepoint1 0 1)))
               )
               ((and (>= y1 0)(equal y1 y2 0.001))
               	   (setq dirxy "N")
               	   (setq coor (cadr (trans usepoint1 0 1)))
               )
               ((and (>= x1 0)(equal x1 x2 0.001))
               	   (setq dirxy "E")
               	   (setq coor (car (trans usepoint1 0 1)))
               )
           )
        )
       
    )
    (if (< (atoi (rtos (abs coor)))  10) 
      (setq cord (strcat "00" (rtos (abs coor))))
      (progn
        (if (< (atoi (rtos (abs coor))) 100)
          (setq cord (strcat "0" (rtos (abs coor))))
          (setq cord (rtos (abs coor))
                len (- (strlen (itoa (atoi (rtos (abs coor))))) 2)
          )
        )
    )  )
    (setq sub "0")
    (while (= sub "0")
         (setq sub (substr cord (strlen cord) 1))
         (if (= sub "0")
              (setq cord (substr cord 1 (1- (strlen cord))))
         )
    )
    (if (= "." (substr cord (strlen cord) 1))
        (setq cord (substr cord 1 (1- (strlen cord))))
    )
    (if (= "-" (substr cord 1 1))
        (setq cord (substr cord 2 (strlen cord)))
    )
    (setq part1 (substr cord 1 len)
          part2 (substr cord (1+ len) (strlen cord))
          coord (strcat dirxy " " part1 "+" part2)
    )
    (smlayer _COORDS)
    (princ)
    (setq inspt (getpoint "\nStarting point of text: ")
          rot (getpoint inspt "\nRotation of text: ")
          txtstyle (assoc "T1" MED_TXT_STYLE_MAP)
    )
    (if (not (tblsearch "style" (nth 1 txtstyle)))
      (MEDMakeTextStyle txtstyle)
    )
    (command "text" "s" (nth 1 txtstyle) inspt rot coord )
    (setvar "OSMODE" orgosmode)
    (princ)
)
	
(defun c:sect( / pt1 pt2 val)
    (med_cur_set "C:SECT")
    (setq curatdia (getvar "ATTDIA"))
    (smlayer _MEDTEXT)
    (setq pt1 (getpoint "\nPick first section point"))
    (setvar "orthomode" 1)
    (setq pt2 (getpoint "\nPick second section point" pt1))
    (setq val (getstring "\nEnter section letter <A>: "))
    (setvar "attdia" 0)
    (command "insert" "sect1" pt1 (* 1.0 _SC) "" pt2 )
    (command "insert" "sect" pt1 (* 1.0 _SC) "" "" val)
    (command "copy" "l" "" pt1 pt2)
    (command "insert" "sect2" pt2 (* 1.0 _SC) "" pt1)
    (setvar "ATTDIA" curatdia)
    (med_ret_ok)
	(princ)
)

(defun c:sectd()
    (medblkins _MEDTEXT "sect-dyn" nil nil (* _SC _PLOTSCALE) 0)
	(princ)
)

(defun c:isolate()
  (setq dent (entsel "\nSelect Entity with Detail info: "))
  (if dent
   (progn
    (if (xdataget (car dent) _EQUIP)
      (setq dent (car dent))
      (progn
        (setq dentss (ssget "C" (nth 1 dent) (nth 1 dent))
		    sslen  (sslength dentss)
		    cnt    0
		    dent   (ssname dentss cnt)
        )
        (while (not (xdataget dent _EQUIP))
		  (setq cnt (1+ cnt)
			dent (ssname dentss cnt)
		  )
        )
      )
    )
    (setq data (xdataget dent _EQUIP)
          dcode(nth 2 data)
    )
   )
   (progn
    (setq dcode (getint "\nCode value to be used: "))
   )
  )
  (setq isolayer (list "MED_TEMP_ISOLATE" "cyan" "continuous")
        cntval (medcount _EQUIP dcode nil nil nil nil nil nil)
  )
  (smlayer  isolayer)
  (setq num (sslength _COUNTSS)
        cnt 0
        ISO_LIST nil 
        _CURRLAY (getvar "CLAYER")
  )
  (while (< cnt num)
    (setq ent (ssname _COUNTSS cnt)
          data(entget ent)
          entlay (dxf 8 data)
          ISO_LIST (append ISO_LIST (list (list ent entlay)))
          cnt (1+ cnt)
    )
  )  
  (command "change" _COUNTSS "" "P" "LA" (nth 0 isolayer) "")
  (command "layer" "F" "*" "")
)
(defun c:unisolate()
  (foreach entgrp ISO_LIST
      (setq ent (nth 0 entgrp)
            entlay (nth 1 entgrp)
            data (entget ent)
            new (cons 8 entlay)
            old (assoc 8 data)
            data (subst new old data)
      )
      (entmod data)
  )
  (command "layer" "t" "*" "s" _CURRLAY "")
  (command "REGEN")
)

(defun c:MEDstrip()
   (prompt "\nMEDSTRIP Select Entities to strip XDATA from: ")
   (setq stripset (ssget)
         stripnum (sslength stripset)
         stripcnt 0
   )
   (while (< stripcnt stripnum)
      (setq stripent  (ssname stripset stripcnt)
            strip_apps(xd_apps stripent)
      )
      (foreach st_app strip_apps
         (xdstrip stripent st_app)
      )
      (setq stripcnt (1+ stripcnt))
   )
   (prompt "\nXdata has been removed!")
)

(defun c:chgsize( / newsz chgapp chgss chglen allsiz taglst codlst sizlst
                    dislst msrlst altlst dptlst rtglst medtag medsiz medcod
                    medmsr meddis medalt meddpt xdlist)
  (prompt "\nSelect Entities to change Size: ")
  (setq chgss  (ssget)
        chglen (sslength chgss)
        chgcnt 0
        allsiz(list 0.5 0.75 1.0 1.25 1.5 2.0 2.5 3.0 3.5 4.0 5.0 6.0)
;        allsiz(list 0.0 0.5 0.75 1.0 1.25 1.5 1.625 1.75 
;                    2.0 2.5 3.0 3.5 4.0 5.0 6.0 9.00 12.00
;                    18.00 24.00 30.0 36.0
;              )
        
  )
  (initget "COnduit Fitting")
  (setq chgapp (getkword "\nChange COnduit or Fitting <CO>: "))
  (while (not (member newsz allsiz))
     (setq newsz (getreal "\nNew Size for Selected Entities: "))
  )
  (cond
    ((or (= chgapp "") (= chgapp "COnduit") (= chgapp nil))
       (setq chgapp _CONDUIT)
    )
    ((= chgapp "CAble")
       (setq chgapp _CABLE)
    )
    ((= chgapp "Tray")
       (setq chgapp _TRAY)
    )
    ((= chgapp "Fitting")
       (setq chgapp _FITTING)
    )
  )
  (while (< chgcnt chglen)
     (setq chgent (ssname chgss chgcnt)
           appdata(xdataget chgent chgapp)
     )
     (if appdata
       (progn
        (setq applen (eval (read (strcat "len" (substr chgapp 4))))
              numtag (/ (1- (length appdata)) applen)
              tagcnt 0
              taglst nil
              codlst nil
              sizlst nil
              dislst nil
              msrlst nil
              altlst nil
              dptlst nil
              rtglst nil
        )
        (repeat numtag
           (setq medtag (nth (+ 1 (* applen tagcnt)) appdata)
                 medsiz (nth (+ 2 (* applen tagcnt)) appdata)
                 medsiz newsz
                 medcod (nth (+ 3 (* applen tagcnt)) appdata)
           )
           (cond
             ((= chgapp _CONDUIT)
                (setq meddis (nth (+ 4 (* applen tagcnt)) appdata)
                      medmsr (nth (+ 5 (* applen tagcnt)) appdata)
                )
             )         
             ((= chgapp _CABLE)
                (setq medrtg (nth (+ 4 (* applen tagcnt)) appdata)
                      meddis (nth (+ 5 (* applen tagcnt)) appdata)
                      medmsr (nth (+ 6 (* applen tagcnt)) appdata)
                )
             )
             ((= chgapp _TRAY)
                (setq meddis (nth (+ 4 (* applen tagcnt)) appdata)
                      meddpt (nth (+ 5 (* applen tagcnt)) appdata)
                      medmsr (nth (+ 6 (* applen tagcnt)) appdata)
                )
             )         
             ((= chgapp _FITTING)
                (setq medalt (nth (+ 4 (* applen tagcnt)) appdata)
                      meddpt (nth (+ 5 (* applen tagcnt)) appdata)
                )
             )
           )
           (setq taglst (append taglst (list medtag))
                 sizlst (append sizlst (list medsiz))
                 codlst (append codlst (list medcod))
                 dislst (append dislst (list meddis))
                 msrlst (append msrlst (list medmsr))
                 rtglst (append rtglst (list medrtg))
                 altlst (append altlst (list medalt))
                 dptlst (append dptlst (list meddpt))
                 tagcnt (1+ tagcnt)
           )
        )
        (cond
          ((= chgapp _CONDUIT)
              (setq xdlist (bld_conduit codlst sizlst taglst dislst msrlst))
              (xdatadd chgent xdlist)
          )         
          ((= chgapp _CABLE)
              (setq xdlist (bld_cable codlst sizlst taglst rtglst dislst msrlst))
              (xdatadd chgent xdlist)
          )
          ((= chgapp _TRAY)
              (setq xdlist (bld_tray codlst sizlst taglst dislst dptlst msrlst))
              (xdatadd chgent xdlist)
          )         
          ((= chgapp _FITTING)
              (setq xdlist (bld_fitting codlst sizlst taglst altlst dptlst))
              (xdatadd chgent xdlist)
          )         
        )
       )
     )
     (setq chgcnt (1+ chgcnt))

  )
)

(defun c:unj ( / ans pt1 pt2 ang blk)
 (ltback nil)
 (if (or (= _CLETT "A") (= _CLETT "B"))
  (progn
  (initget 1 "UNJ UNJC")
  (setq ans (getkword "\nType of fitting UNJ or UNJC: "))
  (if (= ans "UNJ")
    (setq blk (strcat "" "unj" _CLETT))
  )
  (if (= ans "UNJC")
    (setq blk (strcat "" "unjc" _CLETT))
  )
  (setq pt1 (getpoint "\n Insertion point: "))
  (setvar "LASTPOINT" pt1)
  (prompt "\nSelect reference entity: ")
  (setq pt2 (osnap (cadr (entsel)) "perp"))
  (setq ang (angle pt1 pt2))
  (command "insert" (strcat "" "un" _CLETT) pt1 "" "" (angtos (+ ang PI)))
  (setq pt1 (polar pt1 (+ ang 3.14159) 1.1400))
  (command "insert" blk pt1 "" "" pause)
  )
  (prompt "\n Invalid size set conduit size to 1/2 or 3/4\n")
  
 )
)

;
; C:HUBS request info from the user about the type of box desired
; and number of hubs desired
;
(defun c:hubs( / hubpt hinspt bxent bxins refang)
  (med_cur_set "c:hubs")
  (setq hubpt  (nentsel "\nSelect Jbox and location of hub: ")
        hinspt (osnap (cadr hubpt) "MID")
        bxent  (entget (car (last hubpt)))
        bxins  (dxf 10 bxent)
        refang (angle hinspt bxins)
  )
  (cond
   ((= refang (* PI 1.25))
      (progn
         (if (< (distance hinspt bxins) 6.805)
             (jbhub 2.5 "0 1 2"   "jbhub4" hinspt (* PI 1.5))
             (jbhub 3.0 "0 1 2 3" "jbhub8" hinspt (* PI 1.5))
         )
      )
   )       
   ((= refang (* PI 1.75))
      (progn
         (if (< (* _PLOTSCALE (distance hinspt bxins)) (* _PLOTSCALE 6.805))
             (jbhub 2.5 "0 1 2"   "jbhub4" hinspt (* PI 0.5))
             (jbhub 3.0 "0 1 2 3" "jbhub8" hinspt (* PI 0.5))
         )
      )
   )       
   ((= refang (* PI 1.5))
      (progn
         (if (< (* _PLOTSCALE (distance hinspt bxins)) (* _PLOTSCALE 6.805))
          (progn
           (if (/= (dxf 2 bxent) "JBOX8X4")
             (jbhub 2.5 "0 1 2"   "jbhub4" hinspt 0.0)
             (jbhub 3.0 "0 1 2 3" "jbhub8" hinspt 0.0)
           )
          )
          (progn
           (jbhub 3.0 "0 1 2 3" "jbhub8" hinspt 0.0)
          )
         )
      )
   )
   ((= refang 0.0)
      (progn
         (if (= (dxf 2 bxent) "JBOX4X4")
             (jbhub 2.5 "0 1 2"   "jbhub4" hinspt PI)
             (jbhub 3.0 "0 1 2 3" "jbhub8" hinspt PI)
         )
      )
   )

   ((equal refang 3.6025 0.005)
     (progn
       (jbhub 2.5 "0 1 2"   "jbhub4" hinspt (* PI 1.5))
     )
   )
   ((equal refang 5.8195 0.0005)
     (progn
       (jbhub 2.5 "0 1 2"   "jbhub4" hinspt (* PI 0.5))
     )
   )
  )
  (med_ret_ok)
  (princ)
)

(defun c:detagupd( / index_val max_y max_x result tlist1 tlist2 fname fn)
   (med_cur_set "c:detagupd")

   (setq detail_lst (getdettags))
   (if (> (setq index_val (load_dialog "MED")) 0)
      (progn
         (if (new_dialog "Med_Details" index_val)
            (progn 
                (start_list "detaglist")
                (foreach itemtag tagdisplay
                   (add_list itemtag)
                )
                (end_list)
                (action_tile "detaglist" "(prc_detlist $value)")
                (action_tile "updsel"    "(done_dialog 1)")
                (action_tile "cancel"    "(done_dialog 0)")
                (setq result (start_dialog))
            )
         )
         (unload_dialog index_val)
         (if (= result 1)
            (upd_detaglst)
         )

      )
   )
   (med_ret_ok)
   (princ)
)

;;; Shared BOM writer: clears this drawing's MEDProject rows for the current
;;; user/project/path, then sends each entity in SS to the BOM. SS nil = no-op.
(defun MEDBomFromSelection (ss / allsslen allcnt boment)
	(if (and ss (> (sslength ss) 0))
		(progn
			(princ "\nDeleting Old Records")
			(MEDProcessSQLStatement (strcat "DELETE FROM MEDProject WHERE ITEM_DWG_='" (getvar "DWGNAME") "' AND PROJECTNO='" _MEDPROJECT "' AND ITEM_PATH='" (getvar "DWGPREFIX") "' AND USERNAME='" (getvar "loginname") "'" ))
			(setq allsslen (sslength ss)
				  allcnt   0
			)
			(while (< allcnt allsslen)
				(setq boment (ssname ss allcnt))
				(MEDSendEntityDataToBOM boment)
				(setq allcnt (1+ allcnt))
			)
			(princ (strcat "\nBOM updated with " (itoa allsslen) " entit" (if (= allsslen 1) "y." "ies.")))
		)
		(princ "\nNo MED entities to send to BOM.")
	)
	(princ)
)

(defun C:BOM (/ MEDallss)
	(setq MEDallss (ssget "X" (list (list -3 (list "MED*")))))
	(MEDBomFromSelection MEDallss)
)

;;; BOM from a user selection (MED xdata filter). Empty/cancel leaves BOM unchanged.
(defun C:BOMSS (/ ss)
	(princ "\nSelect MED entities for BOM: ")
	(setq ss (ssget (list (list -3 (list "MED*")))))
	(cond
		((null ss)
			(princ "\nBOMSS cancelled or no MED entities in selection. BOM unchanged.")
			(princ)
		)
		(T
			(MEDBomFromSelection ss)
		)
	)
)
;This select statement will create a summary of the QTY.
;select item_type, item_code, item_size, sum(item_qty_) as QTY, itemdesc from medproject
;inner join medtype on item_type=itemtype and item_code=itemcode
;group by Item_type, item_code,item_size, itemdesc order by item_type, item_code
	

(defun MEDFixForExcelParse (StringToFix)
	(if (setq Quotefound (vl-string-search "\"" StringtoFix))
		(progn
			(setq ReturnString StringToFix
				  StartPos 1
			)
			(while Quotefound
				(setq ReturnString (strcat (substr ReturnString 1 QuoteFound) "\"" (substr ReturnString (1+ QuoteFound)))
					  StartPos (+ QuoteFound 2)
					  QuoteFound (vl-string-search "\"" ReturnString StartPos)
				)
			)
		)
		(setq ReturnString StringToFix)
	)
	(if (or (setq CommaFound (vl-string-search "," ReturnString)) StartPos)
		(setq ReturnString (strcat "\"" ReturnString "\""))
	)
	ReturnString
)
	

(defun c:MEDDBBackup()
	(setq MEDTYPEDataBaseRecords (MEDProcessSQLStatement "Select * from MEDTYPE")
	      BackupPathLocation (strcat (getmeddir 1) "\\MEDTYPE-DB-Backup.csv")
	      BackupFileHandle (open BackupPathLocation "w")
    )
	(if BackupFileHandle
		(foreach dbRecord MEDTYPEDatabaseRecords
			(setq RecordLine "")
			(foreach FieldItem dbRecord
				(cond
					((= (type fielditem) 'REAL)
						(setq usethis (itoa (fix fielditem)))
					)
					((not fielditem)
						(setq usethis "")
					)
					(T
						(setq usethis (MEDFixForExcelParse fielditem))
					)
				)
				(setq RecordLine (strcat RecordLine usethis ","))
			)
			(setq RecordLine (substr RecordLine 1 (1- (strlen RecordLine))))
			(write-line RecordLine BackupFileHandle)
		)
	)
	(close BackupFileHandle)
)
(defun C:MEDDBRestore()
	(setq EquipCodeStart (nth 0 (car (cdr (MEDProcessSQLStatement "SELECT MAX(ITEMCODE) from MEDTYPE WHERE ITEMTYPE='EQUIP'"))))
		  selectfile (dcl_SelectFiles (list "*.csv") "Select csv file to Import" (getmeddir 1))
		  DataSetToRestore (getstring "\nProject Name To Restore [ALL for All Projects]: ")
	)
	(if (/= DataSetToRestore "")
		(MEDDatabaseRestore (nth 0 SelectFile) DataSetToRestore)
	)
	
)
(defun MEDDatabaseRestore (FileImportName ProjectToRestore)
	(prompt "\nMED Database Restore utility")
	(setq fileimporthandle (open FileImportname "r")
		  fileimportdata (list)
	)
	(while (setq linedata (read-line fileimporthandle))
		(setq fileimportdata (append fileimportdata (list (mparse linedata "," "\"" nil))))
	)
	(close fileimporthandle)
	(if (/= ProjectToRestore "ALL")
		(progn
			(setq DatatoRestore (list))
			(foreach RecordItem (cdr FileImportData)
				(if (= (car (reverse RecordItem)) ProjectToRestore)
					(setq DatatoRestore (append DataToRestore (list recordItem)))
				)
			)
		)
		(setq DatatoRestore (cdr FileimportData))
	)
	
	;(initget "Yes No")
	;(setq DeleteRecords (getkword "\nDeleteRecords prior to restore [Yes/No]:"))
	;(if (= DeleteRecords "Yes")
	;	(progn
			
)
;;;started a change tag command 08/12/2014
(defun c:chgtag( / newsz chgapp chgss chglen allsiz taglst codlst sizlst
                    dislst msrlst altlst dptlst rtglst medtag medsiz medcod
                    medmsr meddis medalt meddpt xdlist)
  (prompt "\nSelect Entities to change TAG: ")
  (setq chgss  (ssget)
        chglen (sslength chgss)
        chgcnt 0
        allsiz(list 0.5 0.75 1.0 1.25 1.5 2.0 2.5 3.0 3.5 4.0 5.0 6.0)
;        allsiz(list 0.0 0.5 0.75 1.0 1.25 1.5 1.625 1.75 
;                    2.0 2.5 3.0 3.5 4.0 5.0 6.0 9.00 12.00
;                    18.00 24.00 30.0 36.0
;              )
        
  )
  (while (not (member newsz allsiz))
     (setq newsz (getreal "\nNew Size for Selected Entities: "))
  )
  (cond
    ((or (= chgapp "") (= chgapp "COnduit") (= chgapp nil))
       (setq chgapp _CONDUIT)
    )
    ((= chgapp "CAble")
       (setq chgapp _CABLE)
    )
    ((= chgapp "Tray")
       (setq chgapp _TRAY)
    )
    ((= chgapp "Fitting")
       (setq chgapp _FITTING)
    )
  )
  (while (< chgcnt chglen)
     (setq chgent (ssname chgss chgcnt)
           appdata(xdataget chgent chgapp)
     )
     (if appdata
       (progn
        (setq applen (eval (read (strcat "len" (substr chgapp 4))))
              numtag (/ (1- (length appdata)) applen)
              tagcnt 0
              taglst nil
              codlst nil
              sizlst nil
              dislst nil
              msrlst nil
              altlst nil
              dptlst nil
              rtglst nil
        )
        (repeat numtag
           (setq medtag (nth (+ 1 (* applen tagcnt)) appdata)
                 medsiz (nth (+ 2 (* applen tagcnt)) appdata)
                 medsiz newsz
                 medcod (nth (+ 3 (* applen tagcnt)) appdata)
           )
           (cond
             ((= chgapp _CONDUIT)
                (setq meddis (nth (+ 4 (* applen tagcnt)) appdata)
                      medmsr (nth (+ 5 (* applen tagcnt)) appdata)
                )
             )         
             ((= chgapp _CABLE)
                (setq medrtg (nth (+ 4 (* applen tagcnt)) appdata)
                      meddis (nth (+ 5 (* applen tagcnt)) appdata)
                      medmsr (nth (+ 6 (* applen tagcnt)) appdata)
                )
             )
             ((= chgapp _TRAY)
                (setq meddis (nth (+ 4 (* applen tagcnt)) appdata)
                      meddpt (nth (+ 5 (* applen tagcnt)) appdata)
                      medmsr (nth (+ 6 (* applen tagcnt)) appdata)
                )
             )         
             ((= chgapp _FITTING)
                (setq medalt (nth (+ 4 (* applen tagcnt)) appdata)
                      meddpt (nth (+ 5 (* applen tagcnt)) appdata)
                )
             )
           )
           (setq taglst (append taglst (list medtag))
                 sizlst (append sizlst (list medsiz))
                 codlst (append codlst (list medcod))
                 dislst (append dislst (list meddis))
                 msrlst (append msrlst (list medmsr))
                 rtglst (append rtglst (list medrtg))
                 altlst (append altlst (list medalt))
                 dptlst (append dptlst (list meddpt))
                 tagcnt (1+ tagcnt)
           )
        )
        (cond
          ((= chgapp _CONDUIT)
              (setq xdlist (bld_conduit codlst sizlst taglst dislst msrlst))
              (xdatadd chgent xdlist)
          )         
          ((= chgapp _CABLE)
              (setq xdlist (bld_cable codlst sizlst taglst rtglst dislst msrlst))
              (xdatadd chgent xdlist)
          )
          ((= chgapp _TRAY)
              (setq xdlist (bld_tray codlst sizlst taglst dislst dptlst msrlst))
              (xdatadd chgent xdlist)
          )         
          ((= chgapp _FITTING)
              (setq xdlist (bld_fitting codlst sizlst taglst altlst dptlst))
              (xdatadd chgent xdlist)
          )         
        )
       )
     )
     (setq chgcnt (1+ chgcnt))

  )
)
(princ "Done.")
